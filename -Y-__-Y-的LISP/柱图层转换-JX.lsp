;;;; 姜雄 2015-10-30 星期五 天气阴雨 
;;;;柱图层转换

(defun c:317()
(SETVAR "CMDECHO" 0)

(princ "选择需要转换图层实体\n")
(setq P1 (getpoint "选取左上角点！\n"))
(setq P2 (getcorner P1 "选取右下角点！\n"))
(setq sel  (ssget "C" P1 P2))  
(if (/= sel Nil) 
(progn
(setq aa (sslength  sel))
(setq ii 0)
(while (< ii aa)
(setq first  (ssname sel ii)) 
(setq lst (entget first))
(setq laname (cdr (assoc 8 lst))) 
(setq ltype  (cdr (assoc 0 lst))) 

(cond
  ((= laname "柱表文字")     
    (progn  
      (setq new (cons 8 "S-DETL-TEXT"))
      (setq lst (subst new (assoc 8 lst) lst))  
      (setq new2 (cons 7 "TSSD_REIN"))
      (setq lst (subst new2 (assoc 7 lst) lst))  
      (setq new3 (cons 40 300))
      (setq lst (subst new3 (assoc 40 lst) lst))
      (setq new4 (cons 41 0.75))
      (setq lst (subst new4 (assoc 41 lst) lst))    
      (entmod lst)  
    )
  )
  ((= laname "柱表边线")
      (progn  
      (setq new (cons 8 "S-DETL-TEXT"))
      (setq lst (subst new (assoc 8 lst) lst))      
      (entmod lst)  
    )   
   )
  ((= laname "柱尺寸标注")
      (progn  
      (setq new (cons 8 "S-DETL-DIM"))
      (setq lst (subst new (assoc 8 lst) lst))
      (setq new1 (cons 3 "25-100")) 
      (setq lst (subst new1 (assoc 3 lst) lst))  
      (command "-dimstyle" "A" first "") 
      (entmod lst)  
    )   
   )
  ((= laname "砼柱")
      (progn  
      (setq new (cons 8 "S-DETL-LINE1"))
      (setq lst (subst new (assoc 8 lst) lst))      
      (entmod lst)  
    )   
   )
   ((= laname "柱纵筋")
      (progn  
      (setq new (cons 8 "S-DETL-RBAR"))
      (setq lst (subst new (assoc 8 lst) lst))      
      (entmod lst)  
    )   
   )
   ((= laname "柱箍筋")
      (progn  
      (setq new (cons 8 "S-DETL-RBAR"))
      (setq lst (subst new (assoc 8 lst) lst))      
      (entmod lst)  
    )   
   )
)
(setq ii (+ ii 1))
)
)
)
 
(setvar "CMDECHO" 1)
(princ "程序运行正确\n")
)

;;;(setq sel (ssget "all" '((8 . "柱尺寸标注"))))
;;;;(setq ba (entget sel))
;;;(setq ba (subst (cons 8 "S-DETL-DIM") (assoc 8 ba) ba))
;;;(entmod sel) 
;;;;(command "erase" sel "")
;;;(entget (entlast)  )
