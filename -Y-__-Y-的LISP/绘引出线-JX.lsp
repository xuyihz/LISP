;;;; @-Y-__-Y- 2016-5-10 星期二 天气阴雨 
;;;;加载自定义程序




(defun c:79() ;;;绘制引出线               
(SETVAR "CMDECHO" 0)	
(HYCX "文字内容" 0)
(setvar "CMDECHO" 1)
(princ "已插入\n")
)

(defun c:799() ;;;绘制引出线               
(SETVAR "CMDECHO" 0)	
(HYCX "楼层梁" 1)
(setvar "CMDECHO" 1)
(princ "已插入\n")
)

(defun c:731() ;;;绘制引出线              
(SETVAR "CMDECHO" 0)	
(HYCX "文字内容" 1)
(setvar "CMDECHO" 1)
(princ "已插入\n")
)

(defun c:733() ;;;绘制引出线              
(SETVAR "CMDECHO" 0)	
(HYCX "文字内容" 3)
(setvar "CMDECHO" 1)
(princ "已插入\n")
)

(defun c:791() ;;;插入柱名              
(SETVAR "CMDECHO" 0)	
(HYCX2 "KZ1" "S-COLU-TEXT" 550);;;850
(setvar "CMDECHO" 1)
(princ "已插入\n")
)
(defun c:792() ;;;插入柱名              
(SETVAR "CMDECHO" 0)	
(HYCX2 "KZ2" "S-COLU-TEXT" 550);;;850
(setvar "CMDECHO" 1)
(princ "已插入\n")
)
(defun c:793() ;;;插入柱名              
(SETVAR "CMDECHO" 0)	
(HYCX2 "KZ3" "S-COLU-TEXT" 550);;;850
(setvar "CMDECHO" 1)
(princ "已插入\n")
)
(defun c:794() ;;;插入柱名              
(SETVAR "CMDECHO" 0)	
(HYCX2 "KZ4" "S-COLU-TEXT" 550);;;850
(setvar "CMDECHO" 1)
(princ "已插入\n")
)
(defun c:795() ;;;插入柱名              
(SETVAR "CMDECHO" 0)	
(HYCX2 "KZ5" "S-COLU-TEXT" 550);;;850
(setvar "CMDECHO" 1)
(princ "已插入\n")
)
(defun c:796() ;;;插入柱名              
(SETVAR "CMDECHO" 0)	
(HYCX2 "KZ6" "S-COLU-TEXT" 550);;;850
(setvar "CMDECHO" 1)
(princ "已插入\n")
)


(defun c:7911() ;;;绘制引出线               
(SETVAR "CMDECHO" 0)	
(HYCX2 "GBZ1a" "S-COLU-TEXT" 1000)
(setvar "CMDECHO" 1)
(princ "已插入\n")
)
(defun c:7912() ;;;绘制引出线               
(SETVAR "CMDECHO" 0)	
(HYCX2 "GBZ1b" "S-COLU-TEXT" 1000)
(setvar "CMDECHO" 1)
(princ "已插入\n")
)
(defun c:7913() ;;;绘制引出线               
(SETVAR "CMDECHO" 0)	
(HYCX2 "GBZ1c" "S-COLU-TEXT" 1000)
(setvar "CMDECHO" 1)
(princ "已插入\n")
)
(defun c:7914() ;;;绘制引出线               
(SETVAR "CMDECHO" 0)	
(HYCX2 "GBZ1d" "S-COLU-TEXT" 1000)
(setvar "CMDECHO" 1)
(princ "已插入\n")
)

(defun c:7921() ;;;绘制引出线               
(SETVAR "CMDECHO" 0)	
(HYCX2 "GBZ2a" "S-COLU-TEXT" 1000)
(setvar "CMDECHO" 1)
(princ "已插入\n")
)
(defun c:7922() ;;;绘制引出线               
(SETVAR "CMDECHO" 0)	
(HYCX2 "GBZ2b" "S-COLU-TEXT" 1000)
(setvar "CMDECHO" 1)
(princ "已插入\n")
)

(defun c:7923() ;;;绘制引出线               
(SETVAR "CMDECHO" 0)	
(HYCX2 "GBZ2c" "S-COLU-TEXT" 1000)
(setvar "CMDECHO" 1)
(princ "已插入\n")
)

(defun c:7924() ;;;绘制引出线               
(SETVAR "CMDECHO" 0)	
(HYCX2 "GBZ2d" "S-COLU-TEXT" 1000)
(setvar "CMDECHO" 1)
(princ "已插入\n")
)

(defun c:7931() ;;;绘制引出线               
(SETVAR "CMDECHO" 0)	
(HYCX2 "GBZ3a" "S-COLU-TEXT" 1000)
(setvar "CMDECHO" 1)
(princ "已插入\n")
)
(defun c:7932() ;;;绘制引出线               
(SETVAR "CMDECHO" 0)	
(HYCX2 "GBZ3b" "S-COLU-TEXT" 1000)
(setvar "CMDECHO" 1)
(princ "已插入\n")
)
(defun c:7933() ;;;绘制引出线               
(SETVAR "CMDECHO" 0)	
(HYCX2 "GBZ3c" "S-COLU-TEXT" 1000)
(setvar "CMDECHO" 1)
(princ "已插入\n")
)
(defun c:7934() ;;;绘制引出线               
(SETVAR "CMDECHO" 0)	
(HYCX2 "GBZ3d" "S-COLU-TEXT" 1000)
(setvar "CMDECHO" 1)
(princ "已插入\n")
)

(defun c:7941() ;;;绘制引出线               
(SETVAR "CMDECHO" 0)	
(HYCX2 "GBZ4a" "S-COLU-TEXT" 1000)
(setvar "CMDECHO" 1)
(princ "已插入\n")
)
(defun c:7942() ;;;绘制引出线               
(SETVAR "CMDECHO" 0)	
(HYCX2 "GBZ4b" "S-COLU-TEXT" 1000)
(setvar "CMDECHO" 1)
(princ "已插入\n")
)
(defun c:7943() ;;;绘制引出线               
(SETVAR "CMDECHO" 0)	
(HYCX2 "GBZ4c" "S-COLU-TEXT" 1000)
(setvar "CMDECHO" 1)
(princ "已插入\n")
)
(defun c:7944() ;;;绘制引出线               
(SETVAR "CMDECHO" 0)	
(HYCX2 "GBZ4d" "S-COLU-TEXT" 1000)
(setvar "CMDECHO" 1)
(princ "已插入\n")
)


(defun c:7951() ;;;绘制引出线               
(SETVAR "CMDECHO" 0)	
(HYCX2 "GBZ5a" "S-COLU-TEXT" 1000)
(setvar "CMDECHO" 1)
(princ "已插入\n")
)

(defun c:7952() ;;;绘制引出线               
(SETVAR "CMDECHO" 0)	
(HYCX2 "GBZ5b" "S-COLU-TEXT" 1000)
(setvar "CMDECHO" 1)
(princ "已插入\n")
)

(defun c:7953() ;;;绘制引出线               
(SETVAR "CMDECHO" 0)	
(HYCX2 "GBZ5c" "S-COLU-TEXT" 1000)
(setvar "CMDECHO" 1)
(princ "已插入\n")
)

(defun c:7954() ;;;绘制引出线               
(SETVAR "CMDECHO" 0)	
(HYCX2 "GBZ5d" "S-COLU-TEXT" 1000)
(setvar "CMDECHO" 1)
(princ "已插入\n")
)

(defun c:7961() ;;;绘制引出线               
(SETVAR "CMDECHO" 0)	
(HYCX2 "GBZ6a" "S-COLU-TEXT" 1000)
(setvar "CMDECHO" 1)
(princ "已插入\n")
)
(defun c:7962() ;;;绘制引出线               
(SETVAR "CMDECHO" 0)	
(HYCX2 "GBZ6b" "S-COLU-TEXT" 1000)
(setvar "CMDECHO" 1)
(princ "已插入\n")
)
(defun c:7963() ;;;绘制引出线               
(SETVAR "CMDECHO" 0)	
(HYCX2 "GBZ6c" "S-COLU-TEXT" 1000)
(setvar "CMDECHO" 1)
(princ "已插入\n")
)
(defun c:7964() ;;;绘制引出线               
(SETVAR "CMDECHO" 0)	
(HYCX2 "GBZ6d" "S-COLU-TEXT" 1000)
(setvar "CMDECHO" 1)
(princ "已插入\n")
)
(defun c:7965() ;;;绘制引出线               
(SETVAR "CMDECHO" 0)	
(HYCX2 "GBZ6e" "S-COLU-TEXT" 1000)
(setvar "CMDECHO" 1)
(princ "已插入\n")
)
(defun c:7971() ;;;绘制引出线               
(SETVAR "CMDECHO" 0)	
(HYCX2 "GBZ7a" "S-COLU-TEXT" 1000)
(setvar "CMDECHO" 1)
(princ "已插入\n")
)
(defun c:7972() ;;;绘制引出线               
(SETVAR "CMDECHO" 0)	
(HYCX2 "GBZ7b" "S-COLU-TEXT" 1000)
(setvar "CMDECHO" 1)
(princ "已插入\n")
)
(defun c:7973() ;;;绘制引出线               
(SETVAR "CMDECHO" 0)	
(HYCX2 "GBZ7c" "S-COLU-TEXT" 1000)
(setvar "CMDECHO" 1)
(princ "已插入\n")
)









(defun HYCX(LTEXT Num) ;;;绘制引出线 
(setq ss (getvar "osmode"))
(setvar "osmode" 0)
(command "textstyle" "TSSD_REIN")


(command "color" "ByLayer")      
;;;III-绘制引出线
(setq dd (getvar "PLINEWID"))
(SETVAR "PLINEWID" 0)
(setq P3 (getpoint  "选取引出线第一角点！\n"))
(setq P4 (getpoint P3 "选取引出线第二角点！\n"))
(command "pline" P3 P4 "")
(setq P5 (getpoint P4 "选取引出线第一角点！\n"))
(command "pline" P4 P5 "")

(cond ((= Num 0)  (Progn  (setq T1 300) (setq T2 60)))
      ((= Num 1)  (Progn  (setq T1 150)(setq T2 30)))
      ((= Num 2)  (Progn  (setq T1 75)(setq T2 15)))
      ((= Num 3)  (Progn  (setq T1 60)(setq T2 12)))
      ((= Num 7)  (Progn  (setq T1 300)(setq T2 60)))
      ((= Num 8)  (Progn  (setq T1 300)(setq T2 60)))
      ((= Num 9)  (Progn  (setq T1 150)(setq T2 30)))
)

(if (= Num1 0) (princ "不添加文字注释\n")
(progn
(setq P3X (car P3))
(setq P3Y (cadr P3))
(setq P4X (car P4))
(setq P4Y (cadr P4)) 
(setq P5X (car P5))
(setq P5Y (cadr P5))
(setq DX (- P5X P4X))
(setq DY (- P4Y P3Y))
(setq PT1 (list P5X  (+ P5Y T2)  ));;;第一行右端点 
(if  (> DX 0)
(command "text" "J" "BR" PT1  T1 "0" LTEXT)
(command "text" "J" "BL" PT1  T1 "0" LTEXT)
 
)
(entmod lst)
)
)
(setvar "osmode" ss)
(SETVAR "PLINEWID" dd)
)

(defun HYCX2(LTEXT LANAME Leng) ;;;绘制引出线 
(setq ss (getvar "osmode"))
(setvar "osmode" 1)
(command "textstyle" "TSSD_REIN")

(setq chklay  (getvar "clayer"))
(command "clayer" LANAME)
(command "color" "ByLayer")      
;;;III-绘制引出线
(setq dd (getvar "PLINEWID"))
(SETVAR "PLINEWID" 0)
(setq P3 (getpoint  "选取引出线第一角点！\n"))
(setq P4 (getpoint P3 "选取引出线第二角点！\n"))
(setq P3X (car P3))
(setq P3Y (cadr P3))
(setq P4X (car P4))
(setq P4Y (cadr P4)) 
(setq D34X (- P4X P3X))
(setq D34Y (- P4Y P3Y))

(if  (> D34X 0)
	(progn
    (setq NewP3X (- P3X 0))
		(setq NewP4X (+ NewP3X 60))
	    (setq P5X (+ P3X Leng))
	)
    (progn
    (setq NewP3X (+ P3X 0))
		(setq NewP4X (- NewP3X 60))
	    (setq P5X (- P3X Leng))
	)
)
(if  (> D34Y 0)
	(progn
  (setq NewP3Y (- P3Y 0))
		(setq NewP4Y (+ NewP3Y 100))
	    (setq P5Y NewP4Y)
	)
    (progn
    (setq NewP3Y (+ P3Y 0))
		(setq NewP4Y (- P3Y 100))
	    (setq P5Y NewP4Y)
	)
)
(setq NewP3 (list NewP3X NewP3Y ))
(setq NewP4 (list NewP4X NewP4Y ))
(setq P5 (list P5X P5Y ))
(setvar "osmode" 0)
(command "pline" NewP3 NewP4 P5 "")




(progn
(setq P3X (car P3))
(setq P3Y (cadr P3))
(setq DX (- P5X NewP4X))
(setq DY (- NewP4Y P3Y))
(setq PT1 (list NewP4X  (+ NewP4Y 25)  ));;;第一行右端点 
(if  (> DX 0)
(command "text" "J" "BL" PT1  "300" "0" LTEXT)
(command "text" "J" "BR" PT1  "300" "0" LTEXT)
 
)
(entmod lst)
)

(command "clayer" chklay)
(setvar "osmode" ss)
(SETVAR "PLINEWID" dd)
)
