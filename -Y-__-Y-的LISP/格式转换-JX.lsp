;;;; @-Y-__-Y- 2015-12-22 星期二 天气晴
;;;;图层转换
;;;;操作：需要做的就是点选出矩形选择框
;;;;需要注意的是需事先有"TSSD_REIN"文字格式
(defun c:501( / sel aa ii first lst newtext tpre new2);;;
(SETVAR "CMDECHO" 0)
(princ "选择修改为WKL的梁名\n")
(setq newpre "WKL")
(XGQZYY newpre)
(setvar "CMDECHO" 1)
(princ "程序运行正确\n")
)
(defun c:502( / sel aa ii first lst newtext tpre new2);;;
(SETVAR "CMDECHO" 0)
(princ "选择修改为KL的梁名\n")
(setq newpre "KL")
(XGQZYY newpre)
(setvar "CMDECHO" 1)
(princ "程序运行正确\n")
)
(defun c:503( / sel aa ii first lst newtext tpre new2);;;
(SETVAR "CMDECHO" 0)
(princ "选择修改为L的梁名\n")
(setq newpre "L")
(XGQZYY newpre)
(setvar "CMDECHO" 1)
(princ "程序运行正确\n")
)

(defun c:5032( / sel aa ii first lst newtext tpre new2);;;
(SETVAR "CMDECHO" 0)
(princ "选择修改为WL的梁名\n")
(setq newpre "WL")
(XGQZYY newpre)
(setvar "CMDECHO" 1)
(princ "程序运行正确\n")
)
(defun c:504( / sel aa ii first lst newtext tpre new2);;;
(SETVAR "CMDECHO" 0)
(princ "选择修改为KZL的梁名\n")
(setq newpre "KZL")
(XGQZYY newpre)
(setvar "CMDECHO" 1)
(princ "程序运行正确\n")
)
(defun c:505( / sel aa ii first lst newtext tpre new2);;;
(SETVAR "CMDECHO" 0)
(princ "选择修改为XL的梁名\n")
(setq newpre "XL")
(XGQZYY newpre)
(setvar "CMDECHO" 1)
(princ "程序运行正确\n")
)

(defun c:506( / sel aa ii first lst newtext tpre new2);;;
(SETVAR "CMDECHO" 0)
(princ "选择去掉XL的梁名\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq new1 (vl-string-subst "" "(XL)" newtext   ));;;找到(XL)并去掉
(setq new2 (cons 1 new1 ))
(setq lst (subst new2 (assoc 1 lst) lst))
(entmod lst)
(setq ii (+ ii 1))
)
)
)
(setvar "CMDECHO" 1)
(princ "程序运行正确\n")
)


(defun c:507( / sel aa ii first lst newtext tpre new2);;;
(SETVAR "CMDECHO" 0)
(princ "选择改为单边悬挑的梁名\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq Num1 (vl-string-search ")" newtext));;;找到右括号
(setq NewContext (substr newtext Num1 2) )
(cond 
	((= NewContext "A)") (setq New1 (vl-string-subst "A)" "A)" newtext)))
	((= NewContext "B)") (setq New1 (vl-string-subst "A)" "B)" newtext)))
	(T (setq New1 (vl-string-subst "A)" ")" newtext)))
)
(setq new2 (cons 1 new1 ))
(setq lst (subst new2 (assoc 1 lst) lst))
(entmod lst)
(setq ii (+ ii 1))
)
)
)
(setvar "CMDECHO" 1)
(princ "程序运行正确\n")
)

(defun c:508( / sel aa ii first lst newtext tpre new2);;;
(SETVAR "CMDECHO" 0)
(princ "选择改为双边悬挑的梁名\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq Num1 (vl-string-search ")" newtext));;;找到右括号
(setq NewContext (substr newtext Num1 2) )
(cond 
	((= NewContext "A)") (setq New1 (vl-string-subst "B)" "A)" newtext)))
	((= NewContext "B)") (setq New1 (vl-string-subst "B)" "B)" newtext)))
	(T (setq New1 (vl-string-subst "B)" ")" newtext)))
)
(setq new2 (cons 1 new1 ))
(setq lst (subst new2 (assoc 1 lst) lst))
(entmod lst)
(setq ii (+ ii 1))
)
)
)
(setvar "CMDECHO" 1)
(princ "程序运行正确\n")
)

(defun c:511( / sel aa ii first lst newtext tpre new2);;;
(SETVAR "CMDECHO" 0)
(princ "选择无悬挑的梁名\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq Num1 (vl-string-search ")" newtext));;;找到右括号
(setq NewContext (substr newtext Num1 2) )
(cond 
	((= NewContext "A)") (setq New1 (vl-string-subst ")" "A)" newtext)))
	((= NewContext "B)") (setq New1 (vl-string-subst ")" "B)" newtext)))
	(T (setq New1 (vl-string-subst ")" ")" newtext)))
)
(setq new2 (cons 1 new1 ))
(setq lst (subst new2 (assoc 1 lst) lst))
(entmod lst)
(setq ii (+ ii 1))
)
)
)
(setvar "CMDECHO" 1)
(princ "程序运行正确\n")
)

(defun c:515( / sel aa ii first lst newtext tpre new2);;;去掉冒号及后面配筋
(SETVAR "CMDECHO" 0)
(princ "选择配筋\n")
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq Num1 (vl-string-search ";" newtext));;;找到冒号
(setq NewContext (substr newtext 1 Num1) )

(setq new2 (cons 1 NewContext ))
(setq lst (subst new2 (assoc 1 lst) lst))
(entmod lst)
(setq ii (+ ii 1))
)
)
)
(setvar "CMDECHO" 1)
(princ "程序运行正确\n")
)

(defun c:5142( / sel aa ii first lst newtext tpre new2);;;去掉斜杠及后面配筋
;;;由于514原本已经存在故命名5142
(SETVAR "CMDECHO" 0)
(princ "选择配筋\n")
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq Num1 (vl-string-search "/" newtext));;;找到斜杠
(setq NewContext (substr newtext 1 Num1) )

(setq new2 (cons 1 NewContext ))
(setq lst (subst new2 (assoc 1 lst) lst))
(entmod lst)
(setq ii (+ ii 1))
)
)
)
(setvar "CMDECHO" 1)
(princ "程序运行正确\n")
)

(defun c:513( / sel aa ii first lst newtext tpre new2);;;去掉加号及后面配筋
(SETVAR "CMDECHO" 0)
(princ "选择配筋\n")
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq Num1 (vl-string-search "+" newtext));;;找到加号
(setq NewContext (substr newtext 1 Num1) )

(setq new2 (cons 1 NewContext ))
(setq lst (subst new2 (assoc 1 lst) lst))
(entmod lst)
(setq ii (+ ii 1))
)
)
)
(setvar "CMDECHO" 1)
(princ "程序运行正确\n")
)

(defun c:517( / sel aa ii first lst newtext tpre new2);;;去掉空格及后面配筋
(SETVAR "CMDECHO" 0)
(princ "选择配筋\n")
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq Num1 (vl-string-search " " newtext));;;找到空格
(setq NewContext (substr newtext 1 Num1) )

(setq new2 (cons 1 NewContext ))
(setq lst (subst new2 (assoc 1 lst) lst))
(entmod lst)
(setq ii (+ ii 1))
)
)
)
(setvar "CMDECHO" 1)
(princ "程序运行正确\n")
)


(defun c:521( / sel aa ii first lst newtext tpre new2);;;修改梁编号
(SETVAR "CMDECHO" 0)
(initget (+ 1 2 4)) 
(setq Num (getint "\n梁编号：") )
(princ "选择配筋\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq NumRig (vl-string-search "(" newtext));;;找到左括号
(setq NumLef (vl-string-search "L" newtext));;;找到L
(if (/= NumLef Nil)	
	(progn
	(setq NewContext1 (substr newtext 1 (+ NumLef 1) ))
	(setq NewContext2 (substr newtext (+ NumRig 1 )) )
	(setq NewContext (strcat NewContext1 (itoa Num) NewContext2))
)
)
(setq new2 (cons 1 NewContext ))
(setq lst (subst new2 (assoc 1 lst) lst))
(entmod lst)
(setq ii (+ ii 1))
)
)
)
(setvar "CMDECHO" 1)
(princ "程序运行正确\n")
)


(defun c:523( / sel aa ii first lst newtext tpre new2);;;修改梁跨度
(SETVAR "CMDECHO" 0)
(initget (+ 1 2 4)) 
(setq Num (getint "\n梁跨度（不包含悬挑）：") )
(princ "选择配筋\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq NumRig (vl-string-search ")" newtext));;;找到左括号
(setq NumLef (vl-string-search "(" newtext));;;找到L
(if (/= NumLef Nil)	
	(progn
	(setq NewContext1 (substr newtext 1 (+ NumLef 1) ))
	(setq NewContext2 (substr newtext (+ NumRig 1 )) )
	(setq NewContext (strcat NewContext1 (itoa Num) NewContext2))
)
)
(setq new2 (cons 1 NewContext ))
(setq lst (subst new2 (assoc 1 lst) lst))
(entmod lst)
(setq ii (+ ii 1))
)
)
)
(setvar "CMDECHO" 1)
(princ "程序运行正确\n")
)

(defun c:524( / sel aa ii first lst newtext tpre new2);;;修改梁宽
(SETVAR "CMDECHO" 0)
(initget (+ 1 2 4)) 
(setq Num (getint "\n梁宽：") )
(princ "选择配筋\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq NumRig (vl-string-search "x" newtext));;;找到x
(setq NumLef (vl-string-search " " newtext));;;找到空格
(if (/= NumLef Nil)	
	(progn
	(setq NewContext1 (substr newtext 1 (+ NumLef 1) ))
	(setq NewContext2 (substr newtext (+ NumRig 1 )) )
	(setq NewContext (strcat NewContext1 (itoa Num) NewContext2))
)
)
(setq new2 (cons 1 NewContext ))
(setq lst (subst new2 (assoc 1 lst) lst))
(entmod lst)
(setq ii (+ ii 1))
)
)
)
(setvar "CMDECHO" 1)
(princ "程序运行正确\n")
)

(defun c:526( / sel aa ii first lst newtext tpre new2);;;修改梁高
(SETVAR "CMDECHO" 0)
(initget (+ 1 2 4)) 
(setq Num (getint "\n梁高：") )
(princ "选择配筋\n")
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 

(setq NumLef (vl-string-search "x" newtext));;;找到x
(if (/= NumLef Nil)	
	(progn
	(setq NewContext1 (substr newtext 1 (+ NumLef 1) ))
	(setq NewContext (strcat NewContext1 (itoa Num)))
)
)
(setq new2 (cons 1 NewContext ))
(setq lst (subst new2 (assoc 1 lst) lst))
(entmod lst)
(setq ii (+ ii 1))
)
)
)
(setvar "CMDECHO" 1)
(princ "程序运行正确\n")
)

(defun c:519( / sel aa ii first lst newtext tpre new2);;;去掉括号及后面配筋
(SETVAR "CMDECHO" 0)
(princ "选择配筋\n")
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq Num1 (vl-string-search "(" newtext));;;找到左括号
(setq NewContext (substr newtext 1 Num1) )

(setq new2 (cons 1 NewContext ))
(setq lst (subst new2 (assoc 1 lst) lst))
(entmod lst)
(setq ii (+ ii 1))
)
)
)
(setvar "CMDECHO" 1)
(princ "程序运行正确\n")
)

(defun c:510( / sel aa ii first lst newtext tpre new2);;;
(SETVAR "CMDECHO" 0)

(initget (+ 1 2 4)) 
(setq Num (getint "\n前缀序号：") )
(princ "选择修改为梁前缀的梁名\n")
(setq newpre (itoa Num))
(XGQZYY2 newpre)
(setvar "CMDECHO" 1)
(princ "程序运行正确\n")
)



(defun c:51( / sel aa ii first lst laname new2);;;图层相互转换
(SETVAR "CMDECHO" 0)

(setq sel (ssget ) ) 
(if (/= sel Nil) 
(progn
(setq aa (sslength  sel))
(setq ii 0)
(while (< ii aa)
(setq first  (ssname sel ii)) 
(setq lst (entget first))
(setq laname (cdr (assoc 8 lst))) 
(cond    
((= laname "S-BEAM-LINE1")(setq new2 (cons 8 "S-BEAM-LINE2"))) ((= laname "S-BEAM-LINE2")(setq new2 (cons 8 "S-BEAM-LINE1")))
((= laname "S-COLU-HATCH")(setq new2 (cons 8 "S-COLU-HATCH2"))) ((= laname "S-COLU-HATCH2")(setq new2 (cons 8 "S-COLU-HATCH")))
((= laname "S-COLU-LINE1")(setq new2 (cons 8 "S-COLU-LINE2"))) ((= laname "S-COLU-LINE2")(setq new2 (cons 8 "S-COLU-LINE1")))
((= laname "S-WALL-LINE1")(setq new2 (cons 8 "S-WALL-LINE2"))) ((= laname "S-WALL-LINE2")(setq new2 (cons 8 "S-WALL-LINE1")))
((= laname "S-BEAM-X")(setq new2 (cons 8 "-Y-__-Y-的-BEAM-X"))) ((= laname "-Y-__-Y-的-BEAM-X")(setq new2 (cons 8 "S-BEAM-X")))
((= laname "S-BEAM-Y")(setq new2 (cons 8 "-Y-__-Y-的-BEAM-Y"))) ((= laname "-Y-__-Y-的-BEAM-Y")(setq new2 (cons 8 "S-BEAM-Y")))
(T (setq new2 (cons 8 laname)))
 )
(setq lst (subst new2 (assoc 8 lst) lst))
(entmod lst) 
(setq ii (+ ii 1))
)
)
)  
(setvar "CMDECHO" 1)
(princ "程序运行正确\n")
)

(defun c:52( / sel aa ii first lst laname new2);;;文本匹配
(SETVAR "CMDECHO" 0)
(princ "选择匹配源文字\n")
(setq sel (ssget  ":S" '((0 . "TEXT")) ))
(princ "选择被匹配文字\n")
(setq first  (ssname sel 0)) 
(setq lst (entget first)) 
(setq newtext (cdr (assoc 1 lst))) 
(setq new1 (cons 1 newtext))
(XZZHYY new1 1)  
(setvar "CMDECHO" 1)
(princ "程序运行正确\n")
)



 


(defun c:99LTCXSZHYY( / sel aa ii first lst laname new2);;;梁线虚实转换
(SETVAR "CMDECHO" 0)

(setq sel (ssget '((-4 . "<or")(8 . "S-COLU-LINE1")(8 . "S-COLU-HATCH") (-4 . "or>")) ) ) 
(if (/= sel Nil) 
(progn
(setq aa (sslength  sel))
(setq ii 0)
(while (< ii aa)
(setq first  (ssname sel ii)) 
(setq lst (entget first))
(setq laname (cdr (assoc 8 lst))) 
(cond    ((= laname "S-COLU-LINE1")(setq new2 (cons 8 "B-COLU-LINE1"))) ((= laname "B-COLU-HATCH")(setq new2 (cons 8 "S-COLU-HATCH"))) )
(setq lst (subst new2 (assoc 8 lst) lst))
(entmod lst) 
(setq ii (+ ii 1))
)
)
)  
(setvar "CMDECHO" 1)
(princ "程序运行正确\n")
)




(defun c:99ZTCXSZHYY( / sel aa ii first lst laname new2) ;;;柱线虚实转换
(SETVAR "CMDECHO" 0)

(setq sel (ssget '((-4 . "<or")(8 . "S-COLU-LINE1")(8 . "S-COLU-LINE2") (-4 . "or>")) ) ) 
(if (/= sel Nil) 
(progn
(setq aa (sslength  sel))
(setq ii 0)
(while (< ii aa)
(setq first  (ssname sel ii)) 
(setq lst (entget first))
(setq laname (cdr (assoc 8 lst))) 
(cond    ((= laname "S-COLU-LINE1")(setq new2 (cons 8 "S-COLU-LINE2"))) ((= laname "S-COLU-LINE2")(setq new2 (cons 8 "S-COLU-LINE1"))) )
(setq lst (subst new2 (assoc 8 lst) lst))
(entmod lst) 
(setq ii (+ ii 1))
)
)
)  
(setvar "CMDECHO" 1)
(princ "程序运行正确\n")
)

(defun c:9923( / sel aa ii first lst laname new2) ;;;梁面积图层转换
(SETVAR "CMDECHO" 0)
(setq chklay (tblsearch "layer" "dsptext_beam_X")) 
(if (= chklay nil) (command "layer" "n" "dsptext_beam_X" "c" "7" "dsptext_beam_X"  "") )
(setq chklay (tblsearch "layer" "dsptext_beam_Y")) 
(if (= chklay nil) (command "layer" "n" "dsptext_beam_Y" "c" "7" "dsptext_beam_Y"  "") )
(setq t1 (/ PI 4))
(setq t2 (* t1 3))
(setq t3 (* t1 5))
(setq t4 (* t1 7))

(setq sel (ssget '((8 . "dsptext_beam")) ) ) 
(if (/= sel Nil) 
(progn
(setq aa (sslength  sel))
(setq ii 0)
(while (< ii aa)
(setq first  (ssname sel ii)) 
(setq lst (entget first))
(setq angle1 (cdr (assoc 50 lst))) ;;; 得到旋转角度
(if  (or  (and (>= angle1 t1) (<= angle1 t2))  (and (>= angle1 t3) (<= angle1 t4))  )
(setq new2 (cons 8 "dsptext_beam_Y"))
(setq new2 (cons 8 "dsptext_beam_X"))
)
(setq lst (subst new2 (assoc 8 lst) lst))
(entmod lst) 
(setq ii (+ ii 1))
)
)
)
(setvar "CMDECHO" 1)
(princ "程序运行正确\n")
)  



(defun c:9926( / sel aa ii first lst laname new2) ;;;梁面积图层转换
(SETVAR "CMDECHO" 0)
(setq chklay (tblsearch "layer" "dsptext_beam1")) 
(if (= chklay nil) (command "layer" "n" "dsptext_beam1" "c" "173" "dsptext_beam1"  "") )


(setq sel (ssget '((8 . "dsptext_beam")) ) ) 
(if (/= sel Nil) 
(progn
(setq aa (sslength  sel))
(setq ii 0)
(while (< ii aa)
(setq first  (ssname sel ii)) 
(setq lst (entget first))
(setq new2 (cons 8 "dsptext_beam1"))
(setq lst (subst new2 (assoc 8 lst) lst))
(entmod lst) 
(setq ii (+ ii 1))
)
)
)
(setvar "CMDECHO" 1)
(princ "程序运行正确\n")
)  

(defun c:9927( / sel aa ii first lst laname new2) ;;;梁面积图层虚实转换
(SETVAR "CMDECHO" 0)
(setq chklay (tblsearch "layer" "dsptext_beam2")) 
(if (= chklay nil) (command "layer" "n" "dsptext_beam2" "c" "253" "dsptext_beam2"  "") )

(setq sel (ssget '((8 . "dsptext_beam1")) ) ) 
(if (/= sel Nil) 
(progn
(setq aa (sslength  sel))
(setq ii 0)
(while (< ii aa)
(setq first  (ssname sel ii)) 
(setq lst (entget first))
(setq new2 (cons 8 "dsptext_beam2"))
(setq lst (subst new2 (assoc 8 lst) lst))
(entmod lst) 
(setq ii (+ ii 1))
)
)
)  
(setvar "CMDECHO" 1)
(princ "程序运行正确\n")
) 


(defun c:9928( / sel aa ii first lst laname new2) ;;;梁面积图层转换
(SETVAR "CMDECHO" 0)
(setq chklay (tblsearch "layer" "dsptext_beam")) 
(if (= chklay nil) (command "layer" "n" "dsptext_beam" "c" "0" "dsptext_beam"  "") )


(setq sel (ssget '((8 . "dsptext_beam1")) ) ) 
(if (/= sel Nil) 
(progn
(setq aa (sslength  sel))
(setq ii 0)
(while (< ii aa)
(setq first  (ssname sel ii)) 
(setq lst (entget first))
(setq new2 (cons 8 "dsptext_beam"))
(setq lst (subst new2 (assoc 8 lst) lst))
(entmod lst) 
(setq ii (+ ii 1))
)
)
)  
(setvar "CMDECHO" 1)
(princ "程序运行正确\n")
)  







(defun c:100(/ new1 )(SETVAR "CMDECHO" 0)(setq new1 (cons 8 "S-SLAB-TEXT"))(XZZHYY new1 8)(setvar "CMDECHO" 1)(princ "已转换为S-SLAB-TEXT图层\n"))
(defun c:101( / new1)(SETVAR "CMDECHO" 0)(setq new1 (cons 8 "S-SLAB-ROOF"))(XZZHYY new1 8)(setvar "CMDECHO" 1)(princ "已转换为S-SLAB-ROOF图层\n"))
(defun c:105( / new1)(SETVAR "CMDECHO" 0)(setq new1 (cons 8 "S-SLAB-DIM"))(XZZHYY new1 8)(setvar "CMDECHO" 1)(princ "已转换为S-SLAB-DIM图层\n"))
(defun c:106( / new1)(SETVAR "CMDECHO" 0)(setq new1 (cons 8 "S-SLAB-QLLINE"))(XZZHYY new1 8)(setvar "CMDECHO" 1)(princ "已转换为S-SLAB-QLLINE图层\n"))
(defun c:102( / new1 )(SETVAR "CMDECHO" 0)(setq new1 (cons 8 "S-SLAB-RBAR"))(XZZHYY new1 8)(setvar "CMDECHO" 1)(princ "已转换为S-SLAB-RBAR图层\n"))
(defun c:103( / new1 )(SETVAR "CMDECHO" 0)(setq new1 (cons 8 "S-SLAB-RTEXT"))(XZZHYY new1 8)(setvar "CMDECHO" 1)(princ "已转换为S-SLAB-RTEXT图层\n"))
(defun c:104( / new1)(SETVAR "CMDECHO" 0)(setq new1 (cons 8 "S-SLAB-HOLE"))(XZZHYY new1 8)(setvar "CMDECHO" 1)(princ "已转换为S-SLAB-HOLE图层\n"))


(defun c:110( / new1)(SETVAR "CMDECHO" 0)(setq new1 (cons 8 "S-BEAM-TEXT"))(XZZHYY new1 8)(setvar "CMDECHO" 1)(princ "已转换为S-BEAM-TEXT图层\n"))
(defun c:111( / new1)(SETVAR "CMDECHO" 0)(setq new1 (cons 8 "S-BEAM-LINE1"))(XZZHYY new1 8)(setvar "CMDECHO" 1)(princ "已转换为S-BEAM-LINE1图层\n"))
(defun c:112( / new1)(SETVAR "CMDECHO" 0)(setq new1 (cons 8 "S-BEAM-LINE2"))(XZZHYY new1 8)(setvar "CMDECHO" 1)(princ "已转换为S-BEAM-LINE2图层\n"))
(defun c:113( / new1)(SETVAR "CMDECHO" 0)(setq new1 (cons 8 "S-BEAM-X"))(XZZHYY new1 8)(setvar "CMDECHO" 1)(princ "已转换为S-BEAM-X图层\n"))
(defun c:114( / new1)(SETVAR "CMDECHO" 0)(setq new1 (cons 8 "S-BEAM-Y"))(XZZHYY new1 8)(setvar "CMDECHO" 1)(princ "已转换为S-BEAM-Y图层\n"))
(defun c:116( / new1)(SETVAR "CMDECHO" 0)(setq new1 (cons 8 "S-BEAM-XRBAR"))(XZZHYY new1 8)(setvar "CMDECHO" 1)(princ "已转换为S-BEAM-XRBAR图层\n"))
(defun c:117( / new1)(SETVAR "CMDECHO" 0)(setq new1 (cons 8 "S-BEAM-YRBAR"))(XZZHYY new1 8)(setvar "CMDECHO" 1)(princ "已转换为S-BEAM-YRBAR图层\n"))

(defun c:120( / new1)(SETVAR "CMDECHO" 0)(setq new1 (cons 8 "S-COLU-TEXT"))(XZZHYY new1 8)(setvar "CMDECHO" 1)(princ "已转换为S-COLU-TEXT图层\n"))
(defun c:121( / new1)(SETVAR "CMDECHO" 0)(setq new1 (cons 8 "S-COLU-LINE1"))(XZZHYY new1 8)(setvar "CMDECHO" 1)(princ "已转换为S-COLU-LINE1图层\n"))
(defun c:122( / new1)(SETVAR "CMDECHO" 0)(setq new1 (cons 8 "S-COLU-LINE2"))(XZZHYY new1 8)(setvar "CMDECHO" 1)(princ "已转换为S-COLU-LINE2图层\n"))
(defun c:125( / new1)(SETVAR "CMDECHO" 0)(setq new1 (cons 8 "S-COLU-DIM"))(XZZHYY new1 8)(setvar "CMDECHO" 1)(princ "已转换为S-COLU-DIM图层\n"))
(defun c:128( / new1)(SETVAR "CMDECHO" 0)(setq new1 (cons 8 "S-COLU-HATCH"))(XZZHYY new1 8)(setvar "CMDECHO" 1)(princ "已转换为S-COLU-HATCH图层\n"))


(defun c:130( / new1)(SETVAR "CMDECHO" 0)(setq new1 (cons 8 "S-FON-TEXT"))(XZZHYY new1 8)(setvar "CMDECHO" 1)(princ "已转换为S-FON-TEXT图层\n"))
(defun c:131( / new1)(SETVAR "CMDECHO" 0)(setq new1 (cons 8 "S-FON-LINE1"))(XZZHYY new1 8)(setvar "CMDECHO" 1)(princ "已转换为S-FON-LINE1图层\n"))
(defun c:133( / new1 )(SETVAR "CMDECHO" 0)(setq new1 (cons 8 "S-FON-RBAR"))(XZZHYY new1 8)(setvar "CMDECHO" 1)(princ "已转换为S-FON-RBAR图层\n"))
(defun c:135( / new1)(SETVAR "CMDECHO" 0)(setq new1 (cons 8 "S-FON-DIM"))(XZZHYY new1 8)(setvar "CMDECHO" 1)(princ "已转换为S-FON-DIM图层\n"))


(defun c:141( / new1)(SETVAR "CMDECHO" 0)(setq new1 (cons 8 "S-WALL-LINE1"))(XZZHYY new1 8)(setvar "CMDECHO" 1)(princ "已转换为S-WALL-LINE1图层\n"))
(defun c:142( / new1)(SETVAR "CMDECHO" 0)(setq new1 (cons 8 "S-WALL-LINE2"))(XZZHYY new1 8)(setvar "CMDECHO" 1)(princ "已转换为S-WALL-LINE2图层\n"))
(defun c:146( / new1)(SETVAR "CMDECHO" 0)(setq new1 (cons 8 "S-WALL-BELINE"))(XZZHYY new1 8)(setvar "CMDECHO" 1)(princ "已转换为S-WALL-BELINE图层\n"))

(defun c:150( / new1 )(SETVAR "CMDECHO" 0)(setq new1 (cons 8 "S-DETL-TEXT"))(XZZHYY new1 8)(setvar "CMDECHO" 1)(princ "已转换为S-DETL-TEXT图层\n"))
(defun c:151( / new1 )(SETVAR "CMDECHO" 0)(setq new1 (cons 8 "S-DETL-LINE1"))(XZZHYY new1 8)(setvar "CMDECHO" 1)(princ "已转换为S-DETL-LINE1图层\n"))
(defun c:152( / new1 )(SETVAR "CMDECHO" 0)(setq new1 (cons 8 "S-DETL-LINE2"))(XZZHYY new1 8)(setvar "CMDECHO" 1)(princ "已转换为S-DETL-LINE2图层\n"))
(defun c:153( / new1 )(SETVAR "CMDECHO" 0)(setq new1 (cons 8 "S-DETL-RBAR"))(XZZHYY new1 8)(setvar "CMDECHO" 1)(princ "已转换为S-DETL-RBAR图层\n"))
(defun c:155( / new1 )(SETVAR "CMDECHO" 0)(setq new1 (cons 8 "S-DETL-DIM"))(XZZHYY new1 8)(setvar "CMDECHO" 1)(princ "已转换为S-DETL-DIM图层\n"))
(defun c:157( / new1)(SETVAR "CMDECHO" 0)(setq new1 (cons 8 "S-DETL-AXIS"))(XZZHYY new1 8)(setvar "CMDECHO" 1)(princ "已转换为S-DETL-AXIS图层\n"))
(defun c:158( / new1)(SETVAR "CMDECHO" 0)(setq new1 (cons 8 "S-DETL-HATCH"))(XZZHYY new1 8)(setvar "CMDECHO" 1)(princ "已转换为S-DETL-HATCH图层\n"))

(defun c:191(/ new1 )(SETVAR "CMDECHO" 0)(setq new1 (cons 8 "C-DOTE"))(XZZHYY new1 8)(setvar "CMDECHO" 1)(princ "程序运行正确\n"))
(defun c:193(/ new1 )(SETVAR "CMDECHO" 0)(setq new1 (cons 8 "C-ICON"))(XZZHYY new1 8)(setvar "CMDECHO" 1)(princ "程序运行正确\n"))
(defun c:195(/ new1 )(SETVAR "CMDECHO" 0)(setq new1 (cons 8 "C-DIM"))(XZZHYY new1 8)(setvar "CMDECHO" 1)(princ "程序运行正确\n"))
(defun c:194(/ new1 )(SETVAR "CMDECHO" 0)(setq new1 (cons 8 "-Y-__-Y-的配筋修图层"))(XZZHYY new1 8)(setvar "CMDECHO" 1)(princ "程序运行正确\n"))
(defun c:196(/ new1 )(SETVAR "CMDECHO" 0)(setq new1 (cons 8 "-Y-__-Y-的信息图层2"))(XZZHYY new1 8)(setvar "CMDECHO" 1)(princ "程序运行正确\n"))
(defun c:197(/ new1 )(SETVAR "CMDECHO" 0)(setq new1 (cons 8 "-Y-__-Y-的信息图层"))(XZZHYY new1 8)(setvar "CMDECHO" 1)(princ "程序运行正确\n"))
(defun c:199(/ new1 )(SETVAR "CMDECHO" 0)(setq new1 (cons 8 "-Y-__-Y-的辅助图层"))(XZZHYY new1 8)(setvar "CMDECHO" 1)(princ "程序运行正确\n"))


;;;***********转换文字内容********;;;
;;;;;;;;;;;;;;;;;;;;;;;;;;;;;;;;;;;;;;

(defun C:1123(/ new1)(SETVAR "CMDECHO" 0)	(setq new1 (cons 1 "1%%13212"))(XZZHYY new1 1)(setvar "CMDECHO" 1)(princ "已转换\n"))
(defun C:1143(/ new1)(SETVAR "CMDECHO" 0)	(setq new1 (cons 1 "1%%13214"))(XZZHYY new1 1)(setvar "CMDECHO" 1)(princ "已转换\n"))
(defun C:1163(/ new1)(SETVAR "CMDECHO" 0)	(setq new1 (cons 1 "1%%13216"))(XZZHYY new1 1)(setvar "CMDECHO" 1)(princ "已转换\n"))
(defun C:1183(/ new1)(SETVAR "CMDECHO" 0)	(setq new1 (cons 1 "1%%13218"))(XZZHYY new1 1)(setvar "CMDECHO" 1)(princ "已转换\n"))
(defun C:1203(/ new1)(SETVAR "CMDECHO" 0)	(setq new1 (cons 1 "1%%13220"))(XZZHYY new1 1)(setvar "CMDECHO" 1)(princ "已转换\n"))
(defun C:1223(/ new1)(SETVAR "CMDECHO" 0)	(setq new1 (cons 1 "1%%13222"))(XZZHYY new1 1)(setvar "CMDECHO" 1)(princ "已转换\n"))
(defun C:1253(/ new1)(SETVAR "CMDECHO" 0)	(setq new1 (cons 1 "1%%13225"))(XZZHYY new1 1)(setvar "CMDECHO" 1)(princ "已转换\n"))

(defun C:206(/ new1)(SETVAR "CMDECHO" 0)	(setq new1 (cons 1 "2%%1326"))(XZZHYY new1 1)(setvar "CMDECHO" 1)(princ "已转换\n"))
(defun C:212(/ new1)(SETVAR "CMDECHO" 0)	(setq new1 (cons 1 "2%%13212"))(XZZHYY new1 1)(setvar "CMDECHO" 1)(princ "已转换\n"))
(defun C:214(/ new1)(SETVAR "CMDECHO" 0)	(setq new1 (cons 1 "2%%13214"))(XZZHYY new1 1)(setvar "CMDECHO" 1)(princ "已转换\n"))
(defun C:216(/ new1)(SETVAR "CMDECHO" 0)	(setq new1 (cons 1 "2%%13216"))(XZZHYY new1 1)(setvar "CMDECHO" 1)(princ "已转换\n"))
(defun C:218(/ new1)(SETVAR "CMDECHO" 0)	(setq new1 (cons 1 "2%%13218"))(XZZHYY new1 1)(setvar "CMDECHO" 1)(princ "已转换\n"))
(defun C:220(/ new1)(SETVAR "CMDECHO" 0)	(setq new1 (cons 1 "2%%13220"))(XZZHYY new1 1)(setvar "CMDECHO" 1)(princ "已转换\n"))
(defun C:222(/ new1)(SETVAR "CMDECHO" 0)	(setq new1 (cons 1 "2%%13222"))(XZZHYY new1 1)(setvar "CMDECHO" 1)(princ "已转换\n"))
(defun C:225(/ new1)(SETVAR "CMDECHO" 0)	(setq new1 (cons 1 "2%%13225"))(XZZHYY new1 1)(setvar "CMDECHO" 1)(princ "已转换\n"))

(defun C:312(/ new1)(SETVAR "CMDECHO" 0)	(setq new1 (cons 1 "3%%13212"))(XZZHYY new1 1)(setvar "CMDECHO" 1)(princ "已转换\n"))
(defun C:314(/ new1)(SETVAR "CMDECHO" 0)	(setq new1 (cons 1 "3%%13214"))(XZZHYY new1 1)(setvar "CMDECHO" 1)(princ "已转换\n"))
(defun C:316(/ new1)(SETVAR "CMDECHO" 0)	(setq new1 (cons 1 "3%%13216"))(XZZHYY new1 1)(setvar "CMDECHO" 1)(princ "已转换\n"))
(defun C:318(/ new1)(SETVAR "CMDECHO" 0)	(setq new1 (cons 1 "3%%13218"))(XZZHYY new1 1)(setvar "CMDECHO" 1)(princ "已转换\n"))
(defun C:320(/ new1)(SETVAR "CMDECHO" 0)	(setq new1 (cons 1 "3%%13220"))(XZZHYY new1 1)(setvar "CMDECHO" 1)(princ "已转换\n"))
(defun C:322(/ new1)(SETVAR "CMDECHO" 0)	(setq new1 (cons 1 "3%%13222"))(XZZHYY new1 1)(setvar "CMDECHO" 1)(princ "已转换\n"))
(defun C:325(/ new1)(SETVAR "CMDECHO" 0)	(setq new1 (cons 1 "3%%13225"))(XZZHYY new1 1)(setvar "CMDECHO" 1)(princ "已转换\n"))

(defun C:412(/ new1)(SETVAR "CMDECHO" 0)	(setq new1 (cons 1 "4%%13212"))(XZZHYY new1 1)(setvar "CMDECHO" 1)(princ "已转换\n"))
(defun C:414(/ new1)(SETVAR "CMDECHO" 0)	(setq new1 (cons 1 "4%%13214"))(XZZHYY new1 1)(setvar "CMDECHO" 1)(princ "已转换\n"))
(defun C:4142(/ new1)(SETVAR "CMDECHO" 0)	(setq new1 (cons 1 "4%%13214 2/2"))(XZZHYY new1 1)(setvar "CMDECHO" 1)(princ "已转换\n"))
(defun C:4160(/ new1)(SETVAR "CMDECHO" 0)	(setq new1 (cons 1 "4%%13216"))(XZZHYY new1 1)(setvar "CMDECHO" 1)(princ "已转换\n"))
(defun C:4162(/ new1)(SETVAR "CMDECHO" 0)	(setq new1 (cons 1 "4%%13216 2/2"))(XZZHYY new1 1)(setvar "CMDECHO" 1)(princ "已转换\n"))
(defun C:418(/ new1)(SETVAR "CMDECHO" 0)	(setq new1 (cons 1 "4%%13218"))(XZZHYY new1 1)(setvar "CMDECHO" 1)(princ "已转换\n"))
(defun C:420(/ new1)(SETVAR "CMDECHO" 0)	(setq new1 (cons 1 "4%%13220"))(XZZHYY new1 1)(setvar "CMDECHO" 1)(princ "已转换\n"))
(defun C:4202(/ new1)(SETVAR "CMDECHO" 0)	(setq new1 (cons 1 "4%%13220 2/2"))(XZZHYY new1 1)(setvar "CMDECHO" 1)(princ "已转换\n"))
(defun C:422(/ new1)(SETVAR "CMDECHO" 0)	(setq new1 (cons 1 "4%%13222"))(XZZHYY new1 1)(setvar "CMDECHO" 1)(princ "已转换\n"))
(defun C:425(/ new1)(SETVAR "CMDECHO" 0)	(setq new1 (cons 1 "4%%13225"))(XZZHYY new1 1)(setvar "CMDECHO" 1)(princ "已转换\n"))

(defun C:4142(/ new1)(SETVAR "CMDECHO" 0)	(setq new1 (cons 1 "4%%13214 2/2"))(XZZHYY new1 1)(setvar "CMDECHO" 1)(princ "已转换\n"))
(defun C:4182(/ new1)(SETVAR "CMDECHO" 0)	(setq new1 (cons 1 "4%%13218 2/2"))(XZZHYY new1 1)(setvar "CMDECHO" 1)(princ "已转换\n"))

(defun C:512(/ new1)(SETVAR "CMDECHO" 0)	(setq new1 (cons 1 "5%%13212"))(XZZHYY new1 1)(setvar "CMDECHO" 1)(princ "已转换\n"))
(defun C:5143(/ new1)(SETVAR "CMDECHO" 0)	(setq new1 (cons 1 "5%%13214 3/2"))(XZZHYY new1 1)(setvar "CMDECHO" 1)(princ "已转换\n"))
(defun C:516(/ new1)(SETVAR "CMDECHO" 0)	(setq new1 (cons 1 "5%%13216"))(XZZHYY new1 1)(setvar "CMDECHO" 1)(princ "已转换\n"))
(defun C:5163(/ new1)(SETVAR "CMDECHO" 0)	(setq new1 (cons 1 "5%%13216 3/2"))(XZZHYY new1 1)(setvar "CMDECHO" 1)(princ "已转换\n"))
(defun C:5182(/ new1)(SETVAR "CMDECHO" 0)	(setq new1 (cons 1 "5%%13218 2/3"))(XZZHYY new1 1)(setvar "CMDECHO" 1)(princ "已转换\n"))
(defun C:5183(/ new1)(SETVAR "CMDECHO" 0)	(setq new1 (cons 1 "5%%13218 3/2"))(XZZHYY new1 1)(setvar "CMDECHO" 1)(princ "已转换\n"))
(defun C:5202(/ new1)(SETVAR "CMDECHO" 0)	(setq new1 (cons 1 "5%%13220 2/3"))(XZZHYY new1 1)(setvar "CMDECHO" 1)(princ "已转换\n"))
(defun C:5203(/ new1)(SETVAR "CMDECHO" 0)	(setq new1 (cons 1 "5%%13220 3/2"))(XZZHYY new1 1)(setvar "CMDECHO" 1)(princ "已转换\n"))
(defun C:522(/ new1)(SETVAR "CMDECHO" 0)	(setq new1 (cons 1 "5%%13222 2/3"))(XZZHYY new1 1)(setvar "CMDECHO" 1)(princ "已转换\n"))
(defun C:525(/ new1)(SETVAR "CMDECHO" 0)	(setq new1 (cons 1 "5%%13225 2/3"))(XZZHYY new1 1)(setvar "CMDECHO" 1)(princ "已转换\n"))


(defun C:612(/ new1)(SETVAR "CMDECHO" 0)	(setq new1 (cons 1 "6%%13212"))(XZZHYY new1 1)(setvar "CMDECHO" 1)(princ "已转换\n"))
(defun C:614(/ new1)(SETVAR "CMDECHO" 0)	(setq new1 (cons 1 "6%%13214 4/2"))(XZZHYY new1 1)(setvar "CMDECHO" 1)(princ "已转换\n"))
(defun C:6143(/ new1)(SETVAR "CMDECHO" 0)	(setq new1 (cons 1 "6%%13214 3/3"))(XZZHYY new1 1)(setvar "CMDECHO" 1)(princ "已转换\n"))
(defun C:6163(/ new1)(SETVAR "CMDECHO" 0)	(setq new1 (cons 1 "6%%13216 3/3"))(XZZHYY new1 1)(setvar "CMDECHO" 1)(princ "已转换\n"))
(defun C:6164(/ new1)(SETVAR "CMDECHO" 0)	(setq new1 (cons 1 "6%%13216 4/2"))(XZZHYY new1 1)(setvar "CMDECHO" 1)(princ "已转换\n"))
(defun C:6183(/ new1)(SETVAR "CMDECHO" 0)	(setq new1 (cons 1 "6%%13218 3/3"))(XZZHYY new1 1)(setvar "CMDECHO" 1)(princ "已转换\n"))
(defun C:6202(/ new1)(SETVAR "CMDECHO" 0)	(setq new1 (cons 1 "6%%13220 2/4"))(XZZHYY new1 1)(setvar "CMDECHO" 1)(princ "已转换\n"))
(defun C:6203(/ new1)(SETVAR "CMDECHO" 0)	(setq new1 (cons 1 "6%%13220 3/3"))(XZZHYY new1 1)(setvar "CMDECHO" 1)(princ "已转换\n"))
(defun C:6222(/ new1)(SETVAR "CMDECHO" 0)	(setq new1 (cons 1 "6%%13222 2/4"))(XZZHYY new1 1)(setvar "CMDECHO" 1)(princ "已转换\n"))
(defun C:6252(/ new1)(SETVAR "CMDECHO" 0)	(setq new1 (cons 1 "6%%13225 2/4"))(XZZHYY new1 1)(setvar "CMDECHO" 1)(princ "已转换\n"))


(defun C:712(/ new1)(SETVAR "CMDECHO" 0)	(setq new1 (cons 1 "7%%13212 4/3"))(XZZHYY new1 1)(setvar "CMDECHO" 1)(princ "已转换\n"))
(defun C:714(/ new1)(SETVAR "CMDECHO" 0)	(setq new1 (cons 1 "7%%13214 4/3"))(XZZHYY new1 1)(setvar "CMDECHO" 1)(princ "已转换\n"))
(defun C:716(/ new1)(SETVAR "CMDECHO" 0)	(setq new1 (cons 1 "7%%13216 4/3"))(XZZHYY new1 1)(setvar "CMDECHO" 1)(princ "已转换\n"))
(defun C:718(/ new1)(SETVAR "CMDECHO" 0)	(setq new1 (cons 1 "7%%13218 3/4"))(XZZHYY new1 1)(setvar "CMDECHO" 1)(princ "已转换\n"))
(defun C:720(/ new1)(SETVAR "CMDECHO" 0)	(setq new1 (cons 1 "7%%13220 3/4"))(XZZHYY new1 1)(setvar "CMDECHO" 1)(princ "已转换\n"))
(defun C:722(/ new1)(SETVAR "CMDECHO" 0)	(setq new1 (cons 1 "7%%13222 3/4"))(XZZHYY new1 1)(setvar "CMDECHO" 1)(princ "已转换\n"))
(defun C:725(/ new1)(SETVAR "CMDECHO" 0)	(setq new1 (cons 1 "7%%13225 3/4"))(XZZHYY new1 1)(setvar "CMDECHO" 1)(princ "已转换\n"))

(defun C:812(/ new1)(SETVAR "CMDECHO" 0)	(setq new1 (cons 1 "8%%13212 4/4"))(XZZHYY new1 1)(setvar "CMDECHO" 1)(princ "已转换\n"))
(defun C:814(/ new1)(SETVAR "CMDECHO" 0)	(setq new1 (cons 1 "8%%13214 4/4"))(XZZHYY new1 1)(setvar "CMDECHO" 1)(princ "已转换\n"))
(defun C:816(/ new1)(SETVAR "CMDECHO" 0)	(setq new1 (cons 1 "8%%13216 4/4"))(XZZHYY new1 1)(setvar "CMDECHO" 1)(princ "已转换\n"))
(defun C:818(/ new1)(SETVAR "CMDECHO" 0)	(setq new1 (cons 1 "8%%13218 4/4"))(XZZHYY new1 1)(setvar "CMDECHO" 1)(princ "已转换\n"))
(defun C:820(/ new1)(SETVAR "CMDECHO" 0)	(setq new1 (cons 1 "8%%13220 4/4"))(XZZHYY new1 1)(setvar "CMDECHO" 1)(princ "已转换\n"))
(defun C:822(/ new1)(SETVAR "CMDECHO" 0)	(setq new1 (cons 1 "8%%13222 4/4"))(XZZHYY new1 1)(setvar "CMDECHO" 1)(princ "已转换\n"))
(defun C:825(/ new1)(SETVAR "CMDECHO" 0)	(setq new1 (cons 1 "8%%13225 4/4"))(XZZHYY new1 1)(setvar "CMDECHO" 1)(princ "已转换\n"))

(defun C:8122(/ new1)(SETVAR "CMDECHO" 0)	(setq new1 (cons 1 "8%%13212"))(XZZHYY new1 1)(setvar "CMDECHO" 1)(princ "已转换\n"))
(defun C:8142(/ new1)(SETVAR "CMDECHO" 0)	(setq new1 (cons 1 "8%%13214"))(XZZHYY new1 1)(setvar "CMDECHO" 1)(princ "已转换\n"))
(defun C:8162(/ new1)(SETVAR "CMDECHO" 0)	(setq new1 (cons 1 "8%%13216"))(XZZHYY new1 1)(setvar "CMDECHO" 1)(princ "已转换\n"))
(defun C:8182(/ new1)(SETVAR "CMDECHO" 0)	(setq new1 (cons 1 "8%%13218"))(XZZHYY new1 1)(setvar "CMDECHO" 1)(princ "已转换\n"))
(defun C:8202(/ new1)(SETVAR "CMDECHO" 0)	(setq new1 (cons 1 "8%%13220"))(XZZHYY new1 1)(setvar "CMDECHO" 1)(princ "已转换\n"))
(defun C:8222(/ new1)(SETVAR "CMDECHO" 0)	(setq new1 (cons 1 "8%%13222"))(XZZHYY new1 1)(setvar "CMDECHO" 1)(princ "已转换\n"))
(defun C:8252(/ new1)(SETVAR "CMDECHO" 0)	(setq new1 (cons 1 "8%%13225"))(XZZHYY new1 1)(setvar "CMDECHO" 1)(princ "已转换\n"))

(defun C:1012(/ new1)(SETVAR "CMDECHO" 0)	(setq new1 (cons 1 "10%%13212"))(XZZHYY new1 1)(setvar "CMDECHO" 1)(princ "已转换\n"))
(defun C:1014(/ new1)(SETVAR "CMDECHO" 0)	(setq new1 (cons 1 "10%%13214"))(XZZHYY new1 1)(setvar "CMDECHO" 1)(princ "已转换\n"))
(defun C:1016(/ new1)(SETVAR "CMDECHO" 0)	(setq new1 (cons 1 "10%%13216"))(XZZHYY new1 1)(setvar "CMDECHO" 1)(princ "已转换\n"))
(defun C:1018(/ new1)(SETVAR "CMDECHO" 0)	(setq new1 (cons 1 "10%%13218"))(XZZHYY new1 1)(setvar "CMDECHO" 1)(princ "已转换\n"))
(defun C:1020(/ new1)(SETVAR "CMDECHO" 0)	(setq new1 (cons 1 "10%%13220"))(XZZHYY new1 1)(setvar "CMDECHO" 1)(princ "已转换\n"))
(defun C:1022(/ new1)(SETVAR "CMDECHO" 0)	(setq new1 (cons 1 "10%%13222"))(XZZHYY new1 1)(setvar "CMDECHO" 1)(princ "已转换\n"))
(defun C:1025(/ new1)(SETVAR "CMDECHO" 0)	(setq new1 (cons 1 "10%%13225"))(XZZHYY new1 1)(setvar "CMDECHO" 1)(princ "已转换\n"))

(defun C:1214(/ new1)(SETVAR "CMDECHO" 0)	(setq new1 (cons 1 "12%%13214"))(XZZHYY new1 1)(setvar "CMDECHO" 1)(princ "已转换\n"))
(defun C:1216(/ new1)(SETVAR "CMDECHO" 0)	(setq new1 (cons 1 "12%%13216"))(XZZHYY new1 1)(setvar "CMDECHO" 1)(princ "已转换\n"))
(defun C:1218(/ new1)(SETVAR "CMDECHO" 0)	(setq new1 (cons 1 "12%%13218"))(XZZHYY new1 1)(setvar "CMDECHO" 1)(princ "已转换\n"))
(defun C:1220(/ new1)(SETVAR "CMDECHO" 0)	(setq new1 (cons 1 "12%%13220"))(XZZHYY new1 1)(setvar "CMDECHO" 1)(princ "已转换\n"))
(defun C:1222(/ new1)(SETVAR "CMDECHO" 0)	(setq new1 (cons 1 "12%%13222"))(XZZHYY new1 1)(setvar "CMDECHO" 1)(princ "已转换\n"))
(defun C:1225(/ new1)(SETVAR "CMDECHO" 0)	(setq new1 (cons 1 "12%%13225"))(XZZHYY new1 1)(setvar "CMDECHO" 1)(princ "已转换\n"))

(defun C:1414(/ new1)(SETVAR "CMDECHO" 0)	(setq new1 (cons 1 "14%%13214"))(XZZHYY new1 1)(setvar "CMDECHO" 1)(princ "已转换\n"))
(defun C:1416(/ new1)(SETVAR "CMDECHO" 0)	(setq new1 (cons 1 "14%%13216"))(XZZHYY new1 1)(setvar "CMDECHO" 1)(princ "已转换\n"))
(defun C:1418(/ new1)(SETVAR "CMDECHO" 0)	(setq new1 (cons 1 "14%%13218"))(XZZHYY new1 1)(setvar "CMDECHO" 1)(princ "已转换\n"))
(defun C:1420(/ new1)(SETVAR "CMDECHO" 0)	(setq new1 (cons 1 "14%%13220"))(XZZHYY new1 1)(setvar "CMDECHO" 1)(princ "已转换\n"))
(defun C:1422(/ new1)(SETVAR "CMDECHO" 0)	(setq new1 (cons 1 "14%%13222"))(XZZHYY new1 1)(setvar "CMDECHO" 1)(princ "已转换\n"))
(defun C:1425(/ new1)(SETVAR "CMDECHO" 0)	(setq new1 (cons 1 "14%%13225"))(XZZHYY new1 1)(setvar "CMDECHO" 1)(princ "已转换\n"))

(defun C:1614(/ new1)(SETVAR "CMDECHO" 0)	(setq new1 (cons 1 "16%%13214"))(XZZHYY new1 1)(setvar "CMDECHO" 1)(princ "已转换\n"))
(defun C:1616(/ new1)(SETVAR "CMDECHO" 0)	(setq new1 (cons 1 "16%%13216"))(XZZHYY new1 1)(setvar "CMDECHO" 1)(princ "已转换\n"))
(defun C:1618(/ new1)(SETVAR "CMDECHO" 0)	(setq new1 (cons 1 "16%%13218"))(XZZHYY new1 1)(setvar "CMDECHO" 1)(princ "已转换\n"))
(defun C:1620(/ new1)(SETVAR "CMDECHO" 0)	(setq new1 (cons 1 "16%%13220"))(XZZHYY new1 1)(setvar "CMDECHO" 1)(princ "已转换\n"))
(defun C:1622(/ new1)(SETVAR "CMDECHO" 0)	(setq new1 (cons 1 "16%%13222"))(XZZHYY new1 1)(setvar "CMDECHO" 1)(princ "已转换\n"))
(defun C:1625(/ new1)(SETVAR "CMDECHO" 0)	(setq new1 (cons 1 "16%%13225"))(XZZHYY new1 1)(setvar "CMDECHO" 1)(princ "已转换\n"))

(defun C:71()(SETVAR "CMDECHO" 0)	(setq new1 "*")(XZZHYY2 new1)(setvar "CMDECHO" 1)(princ "已转换\n"))

(defun C:3114()(SETVAR "CMDECHO" 0)	(setq new1 "+1%%13214")(XZZHYY2 new1)(setvar "CMDECHO" 1)(princ "已转换\n"))
(defun C:3116()(SETVAR "CMDECHO" 0)	(setq new1 "+1%%13216")(XZZHYY2 new1)(setvar "CMDECHO" 1)(princ "已转换\n"))
(defun C:3118()(SETVAR "CMDECHO" 0)	(setq new1 "+1%%13218")(XZZHYY2 new1)(setvar "CMDECHO" 1)(princ "已转换\n"))
(defun C:3120()(SETVAR "CMDECHO" 0)	(setq new1 "+1%%13220")(XZZHYY2 new1)(setvar "CMDECHO" 1)(princ "已转换\n"))
(defun C:3122()(SETVAR "CMDECHO" 0)	(setq new1 "+1%%13222")(XZZHYY2 new1)(setvar "CMDECHO" 1)(princ "已转换\n"))
(defun C:3125()(SETVAR "CMDECHO" 0)	(setq new1 "+1%%13225")(XZZHYY2 new1)(setvar "CMDECHO" 1)(princ "已转换\n"))


(defun C:3214()(SETVAR "CMDECHO" 0)	(setq new1 "+2%%13214")(XZZHYY2 new1)(setvar "CMDECHO" 1)(princ "已转换\n"))
(defun C:3216()(SETVAR "CMDECHO" 0)	(setq new1 "+2%%13216")(XZZHYY2 new1)(setvar "CMDECHO" 1)(princ "已转换\n"))
(defun C:3218()(SETVAR "CMDECHO" 0)	(setq new1 "+2%%13218")(XZZHYY2 new1)(setvar "CMDECHO" 1)(princ "已转换\n"))
(defun C:3220()(SETVAR "CMDECHO" 0)	(setq new1 "+2%%13220")(XZZHYY2 new1)(setvar "CMDECHO" 1)(princ "已转换\n"))
(defun C:3222()(SETVAR "CMDECHO" 0)	(setq new1 "+2%%13222")(XZZHYY2 new1)(setvar "CMDECHO" 1)(princ "已转换\n"))
(defun C:3225()(SETVAR "CMDECHO" 0)	(setq new1 "+2%%13225")(XZZHYY2 new1)(setvar "CMDECHO" 1)(princ "已转换\n"))

(defun C:3314()(SETVAR "CMDECHO" 0)	(setq new1 "+3%%13214")(XZZHYY2 new1)(setvar "CMDECHO" 1)(princ "已转换\n"))
(defun C:3316()(SETVAR "CMDECHO" 0)	(setq new1 "+3%%13216")(XZZHYY2 new1)(setvar "CMDECHO" 1)(princ "已转换\n"))
(defun C:3318()(SETVAR "CMDECHO" 0)	(setq new1 "+3%%13218")(XZZHYY2 new1)(setvar "CMDECHO" 1)(princ "已转换\n"))
(defun C:3320()(SETVAR "CMDECHO" 0)	(setq new1 "+3%%13220")(XZZHYY2 new1)(setvar "CMDECHO" 1)(princ "已转换\n"))
(defun C:3322()(SETVAR "CMDECHO" 0)	(setq new1 "+3%%13222")(XZZHYY2 new1)(setvar "CMDECHO" 1)(princ "已转换\n"))
(defun C:3325()(SETVAR "CMDECHO" 0)	(setq new1 "+3%%13225")(XZZHYY2 new1)(setvar "CMDECHO" 1)(princ "已转换\n"))


(defun C:3414()(SETVAR "CMDECHO" 0)	(setq new1 "+4%%13214")(XZZHYY2 new1)(setvar "CMDECHO" 1)(princ "已转换\n"))
(defun C:3416()(SETVAR "CMDECHO" 0)	(setq new1 "+4%%13216")(XZZHYY2 new1)(setvar "CMDECHO" 1)(princ "已转换\n"))
(defun C:3418()(SETVAR "CMDECHO" 0)	(setq new1 "+4%%13218")(XZZHYY2 new1)(setvar "CMDECHO" 1)(princ "已转换\n"))
(defun C:3420()(SETVAR "CMDECHO" 0)	(setq new1 "+4%%13220")(XZZHYY2 new1)(setvar "CMDECHO" 1)(princ "已转换\n"))
(defun C:3422()(SETVAR "CMDECHO" 0)	(setq new1 "+4%%13222")(XZZHYY2 new1)(setvar "CMDECHO" 1)(princ "已转换\n"))
(defun C:3425()(SETVAR "CMDECHO" 0)	(setq new1 "+4%%13225")(XZZHYY2 new1)(setvar "CMDECHO" 1)(princ "已转换\n"))


(defun C:3514()(SETVAR "CMDECHO" 0)	(setq new1 "+5%%13214")(XZZHYY2 new1)(setvar "CMDECHO" 1)(princ "已转换\n"))
(defun C:3516()(SETVAR "CMDECHO" 0)	(setq new1 "+5%%13216")(XZZHYY2 new1)(setvar "CMDECHO" 1)(princ "已转换\n"))
(defun C:3518()(SETVAR "CMDECHO" 0)	(setq new1 "+5%%13218")(XZZHYY2 new1)(setvar "CMDECHO" 1)(princ "已转换\n"))
(defun C:3520()(SETVAR "CMDECHO" 0)	(setq new1 "+5%%13220")(XZZHYY2 new1)(setvar "CMDECHO" 1)(princ "已转换\n"))
(defun C:3522()(SETVAR "CMDECHO" 0)	(setq new1 "+5%%13222")(XZZHYY2 new1)(setvar "CMDECHO" 1)(princ "已转换\n"))
(defun C:3525()(SETVAR "CMDECHO" 0)	(setq new1 "+5%%13225")(XZZHYY2 new1)(setvar "CMDECHO" 1)(princ "已转换\n"))

(defun C:3614()(SETVAR "CMDECHO" 0)	(setq new1 "+6%%13214")(XZZHYY2 new1)(setvar "CMDECHO" 1)(princ "已转换\n"))
(defun C:3616()(SETVAR "CMDECHO" 0)	(setq new1 "+6%%13216")(XZZHYY2 new1)(setvar "CMDECHO" 1)(princ "已转换\n"))
(defun C:3618()(SETVAR "CMDECHO" 0)	(setq new1 "+6%%13218")(XZZHYY2 new1)(setvar "CMDECHO" 1)(princ "已转换\n"))
(defun C:3620()(SETVAR "CMDECHO" 0)	(setq new1 "+6%%13220")(XZZHYY2 new1)(setvar "CMDECHO" 1)(princ "已转换\n"))
(defun C:3622()(SETVAR "CMDECHO" 0)	(setq new1 "+6%%13222")(XZZHYY2 new1)(setvar "CMDECHO" 1)(princ "已转换\n"))
(defun C:3625()(SETVAR "CMDECHO" 0)	(setq new1 "+6%%13225")(XZZHYY2 new1)(setvar "CMDECHO" 1)(princ "已转换\n"))

(defun C:4114()(SETVAR "CMDECHO" 0)	(setq new1 "/1%%13214")(XZZHYY2 new1)(setvar "CMDECHO" 1)(princ "已转换\n"))
(defun C:4116()(SETVAR "CMDECHO" 0)	(setq new1 "/1%%13216")(XZZHYY2 new1)(setvar "CMDECHO" 1)(princ "已转换\n"))
(defun C:4118()(SETVAR "CMDECHO" 0)	(setq new1 "/1%%13218")(XZZHYY2 new1)(setvar "CMDECHO" 1)(princ "已转换\n"))
(defun C:4120()(SETVAR "CMDECHO" 0)	(setq new1 "/1%%13220")(XZZHYY2 new1)(setvar "CMDECHO" 1)(princ "已转换\n"))
(defun C:4122()(SETVAR "CMDECHO" 0)	(setq new1 "/1%%13222")(XZZHYY2 new1)(setvar "CMDECHO" 1)(princ "已转换\n"))
(defun C:4125()(SETVAR "CMDECHO" 0)	(setq new1 "/1%%13225")(XZZHYY2 new1)(setvar "CMDECHO" 1)(princ "已转换\n"))


(defun C:4214()(SETVAR "CMDECHO" 0)	(setq new1 "/2%%13214")(XZZHYY2 new1)(setvar "CMDECHO" 1)(princ "已转换\n"))
(defun C:4216()(SETVAR "CMDECHO" 0)	(setq new1 "/2%%13216")(XZZHYY2 new1)(setvar "CMDECHO" 1)(princ "已转换\n"))
(defun C:4218()(SETVAR "CMDECHO" 0)	(setq new1 "/2%%13218")(XZZHYY2 new1)(setvar "CMDECHO" 1)(princ "已转换\n"))
(defun C:4220()(SETVAR "CMDECHO" 0)	(setq new1 "/2%%13220")(XZZHYY2 new1)(setvar "CMDECHO" 1)(princ "已转换\n"))
(defun C:4222()(SETVAR "CMDECHO" 0)	(setq new1 "/2%%13222")(XZZHYY2 new1)(setvar "CMDECHO" 1)(princ "已转换\n"))
(defun C:4225()(SETVAR "CMDECHO" 0)	(setq new1 "/2%%13225")(XZZHYY2 new1)(setvar "CMDECHO" 1)(princ "已转换\n"))

(defun C:4314()(SETVAR "CMDECHO" 0)	(setq new1 "/3%%13214")(XZZHYY2 new1)(setvar "CMDECHO" 1)(princ "已转换\n"))
(defun C:4316()(SETVAR "CMDECHO" 0)	(setq new1 "/3%%13216")(XZZHYY2 new1)(setvar "CMDECHO" 1)(princ "已转换\n"))
(defun C:4318()(SETVAR "CMDECHO" 0)	(setq new1 "/3%%13218")(XZZHYY2 new1)(setvar "CMDECHO" 1)(princ "已转换\n"))
(defun C:4320()(SETVAR "CMDECHO" 0)	(setq new1 "/3%%13220")(XZZHYY2 new1)(setvar "CMDECHO" 1)(princ "已转换\n"))
(defun C:4322()(SETVAR "CMDECHO" 0)	(setq new1 "/3%%13222")(XZZHYY2 new1)(setvar "CMDECHO" 1)(princ "已转换\n"))
(defun C:4325()(SETVAR "CMDECHO" 0)	(setq new1 "/3%%13225")(XZZHYY2 new1)(setvar "CMDECHO" 1)(princ "已转换\n"))


(defun C:4414()(SETVAR "CMDECHO" 0)	(setq new1 "/4%%13214")(XZZHYY2 new1)(setvar "CMDECHO" 1)(princ "已转换\n"))
(defun C:4416()(SETVAR "CMDECHO" 0)	(setq new1 "/4%%13216")(XZZHYY2 new1)(setvar "CMDECHO" 1)(princ "已转换\n"))
(defun C:4418()(SETVAR "CMDECHO" 0)	(setq new1 "/4%%13218")(XZZHYY2 new1)(setvar "CMDECHO" 1)(princ "已转换\n"))
(defun C:4420()(SETVAR "CMDECHO" 0)	(setq new1 "/4%%13220")(XZZHYY2 new1)(setvar "CMDECHO" 1)(princ "已转换\n"))
(defun C:4422()(SETVAR "CMDECHO" 0)	(setq new1 "/4%%13222")(XZZHYY2 new1)(setvar "CMDECHO" 1)(princ "已转换\n"))
(defun C:4425()(SETVAR "CMDECHO" 0)	(setq new1 "/4%%13225")(XZZHYY2 new1)(setvar "CMDECHO" 1)(princ "已转换\n"))


(defun C:4514()(SETVAR "CMDECHO" 0)	(setq new1 "/5%%13214")(XZZHYY2 new1)(setvar "CMDECHO" 1)(princ "已转换\n"))
(defun C:4516()(SETVAR "CMDECHO" 0)	(setq new1 "/5%%13216")(XZZHYY2 new1)(setvar "CMDECHO" 1)(princ "已转换\n"))
(defun C:4518()(SETVAR "CMDECHO" 0)	(setq new1 "/5%%13218")(XZZHYY2 new1)(setvar "CMDECHO" 1)(princ "已转换\n"))
(defun C:4520()(SETVAR "CMDECHO" 0)	(setq new1 "/5%%13220")(XZZHYY2 new1)(setvar "CMDECHO" 1)(princ "已转换\n"))
(defun C:4522()(SETVAR "CMDECHO" 0)	(setq new1 "/5%%13222")(XZZHYY2 new1)(setvar "CMDECHO" 1)(princ "已转换\n"))
(defun C:4525()(SETVAR "CMDECHO" 0)	(setq new1 "/5%%13225")(XZZHYY2 new1)(setvar "CMDECHO" 1)(princ "已转换\n"))

(defun C:4614()(SETVAR "CMDECHO" 0)	(setq new1 "/6%%13214")(XZZHYY2 new1)(setvar "CMDECHO" 1)(princ "已转换\n"))
(defun C:4616()(SETVAR "CMDECHO" 0)	(setq new1 "/6%%13216")(XZZHYY2 new1)(setvar "CMDECHO" 1)(princ "已转换\n"))
(defun C:4618()(SETVAR "CMDECHO" 0)	(setq new1 "/6%%13218")(XZZHYY2 new1)(setvar "CMDECHO" 1)(princ "已转换\n"))
(defun C:4620()(SETVAR "CMDECHO" 0)	(setq new1 "/6%%13220")(XZZHYY2 new1)(setvar "CMDECHO" 1)(princ "已转换\n"))
(defun C:4622()(SETVAR "CMDECHO" 0)	(setq new1 "/6%%13222")(XZZHYY2 new1)(setvar "CMDECHO" 1)(princ "已转换\n"))
(defun C:4625()(SETVAR "CMDECHO" 0)	(setq new1 "/6%%13225")(XZZHYY2 new1)(setvar "CMDECHO" 1)(princ "已转换\n"))


(defun C:5114()(SETVAR "CMDECHO" 0)	(setq new1 ";1%%13214")(XZZHYY2 new1)(setvar "CMDECHO" 1)(princ "已转换\n"))
(defun C:5116()(SETVAR "CMDECHO" 0)	(setq new1 ";1%%13216")(XZZHYY2 new1)(setvar "CMDECHO" 1)(princ "已转换\n"))
(defun C:5118()(SETVAR "CMDECHO" 0)	(setq new1 ";1%%13218")(XZZHYY2 new1)(setvar "CMDECHO" 1)(princ "已转换\n"))
(defun C:5120()(SETVAR "CMDECHO" 0)	(setq new1 ";1%%13220")(XZZHYY2 new1)(setvar "CMDECHO" 1)(princ "已转换\n"))
(defun C:5122()(SETVAR "CMDECHO" 0)	(setq new1 ";1%%13222")(XZZHYY2 new1)(setvar "CMDECHO" 1)(princ "已转换\n"))
(defun C:5125()(SETVAR "CMDECHO" 0)	(setq new1 ";1%%13225")(XZZHYY2 new1)(setvar "CMDECHO" 1)(princ "已转换\n"))


(defun C:5214()(SETVAR "CMDECHO" 0)	(setq new1 ";2%%13214")(XZZHYY2 new1)(setvar "CMDECHO" 1)(princ "已转换\n"))
(defun C:5216()(SETVAR "CMDECHO" 0)	(setq new1 ";2%%13216")(XZZHYY2 new1)(setvar "CMDECHO" 1)(princ "已转换\n"))
(defun C:5218()(SETVAR "CMDECHO" 0)	(setq new1 ";2%%13218")(XZZHYY2 new1)(setvar "CMDECHO" 1)(princ "已转换\n"))
(defun C:5220()(SETVAR "CMDECHO" 0)	(setq new1 ";2%%13220")(XZZHYY2 new1)(setvar "CMDECHO" 1)(princ "已转换\n"))
(defun C:5222()(SETVAR "CMDECHO" 0)	(setq new1 ";2%%13222")(XZZHYY2 new1)(setvar "CMDECHO" 1)(princ "已转换\n"))
(defun C:5225()(SETVAR "CMDECHO" 0)	(setq new1 ";2%%13225")(XZZHYY2 new1)(setvar "CMDECHO" 1)(princ "已转换\n"))

(defun C:5314()(SETVAR "CMDECHO" 0)	(setq new1 ";3%%13214")(XZZHYY2 new1)(setvar "CMDECHO" 1)(princ "已转换\n"))
(defun C:5316()(SETVAR "CMDECHO" 0)	(setq new1 ";3%%13216")(XZZHYY2 new1)(setvar "CMDECHO" 1)(princ "已转换\n"))
(defun C:5318()(SETVAR "CMDECHO" 0)	(setq new1 ";3%%13218")(XZZHYY2 new1)(setvar "CMDECHO" 1)(princ "已转换\n"))
(defun C:5320()(SETVAR "CMDECHO" 0)	(setq new1 ";3%%13220")(XZZHYY2 new1)(setvar "CMDECHO" 1)(princ "已转换\n"))
(defun C:5322()(SETVAR "CMDECHO" 0)	(setq new1 ";3%%13222")(XZZHYY2 new1)(setvar "CMDECHO" 1)(princ "已转换\n"))
(defun C:5325()(SETVAR "CMDECHO" 0)	(setq new1 ";3%%13225")(XZZHYY2 new1)(setvar "CMDECHO" 1)(princ "已转换\n"))


(defun C:5414()(SETVAR "CMDECHO" 0)	(setq new1 ";4%%13214")(XZZHYY2 new1)(setvar "CMDECHO" 1)(princ "已转换\n"))
(defun C:5416()(SETVAR "CMDECHO" 0)	(setq new1 ";4%%13216")(XZZHYY2 new1)(setvar "CMDECHO" 1)(princ "已转换\n"))
(defun C:5418()(SETVAR "CMDECHO" 0)	(setq new1 ";4%%13218")(XZZHYY2 new1)(setvar "CMDECHO" 1)(princ "已转换\n"))
(defun C:5420()(SETVAR "CMDECHO" 0)	(setq new1 ";4%%13220")(XZZHYY2 new1)(setvar "CMDECHO" 1)(princ "已转换\n"))
(defun C:5422()(SETVAR "CMDECHO" 0)	(setq new1 ";4%%13222")(XZZHYY2 new1)(setvar "CMDECHO" 1)(princ "已转换\n"))
(defun C:5425()(SETVAR "CMDECHO" 0)	(setq new1 ";4%%13225")(XZZHYY2 new1)(setvar "CMDECHO" 1)(princ "已转换\n"))


(defun C:5514()(SETVAR "CMDECHO" 0)	(setq new1 ";5%%13214")(XZZHYY2 new1)(setvar "CMDECHO" 1)(princ "已转换\n"))
(defun C:5516()(SETVAR "CMDECHO" 0)	(setq new1 ";5%%13216")(XZZHYY2 new1)(setvar "CMDECHO" 1)(princ "已转换\n"))
(defun C:5518()(SETVAR "CMDECHO" 0)	(setq new1 ";5%%13218")(XZZHYY2 new1)(setvar "CMDECHO" 1)(princ "已转换\n"))
(defun C:5520()(SETVAR "CMDECHO" 0)	(setq new1 ";5%%13220")(XZZHYY2 new1)(setvar "CMDECHO" 1)(princ "已转换\n"))
(defun C:5522()(SETVAR "CMDECHO" 0)	(setq new1 ";5%%13222")(XZZHYY2 new1)(setvar "CMDECHO" 1)(princ "已转换\n"))
(defun C:5525()(SETVAR "CMDECHO" 0)	(setq new1 ";5%%13225")(XZZHYY2 new1)(setvar "CMDECHO" 1)(princ "已转换\n"))

(defun C:5614()(SETVAR "CMDECHO" 0)	(setq new1 ";6%%13214 4/2")(XZZHYY2 new1)(setvar "CMDECHO" 1)(princ "已转换\n"))
(defun C:5616()(SETVAR "CMDECHO" 0)	(setq new1 ";6%%13216 4/2")(XZZHYY2 new1)(setvar "CMDECHO" 1)(princ "已转换\n"))
(defun C:5618()(SETVAR "CMDECHO" 0)	(setq new1 ";6%%13218 3/3")(XZZHYY2 new1)(setvar "CMDECHO" 1)(princ "已转换\n"))
(defun C:5620()(SETVAR "CMDECHO" 0)	(setq new1 ";6%%13220 2/4")(XZZHYY2 new1)(setvar "CMDECHO" 1)(princ "已转换\n"))
(defun C:5622()(SETVAR "CMDECHO" 0)	(setq new1 ";6%%13222 2/4")(XZZHYY2 new1)(setvar "CMDECHO" 1)(princ "已转换\n"))
(defun C:5625()(SETVAR "CMDECHO" 0)	(setq new1 ";6%%13225 2/4")(XZZHYY2 new1)(setvar "CMDECHO" 1)(princ "已转换\n"))

(defun C:5718()(SETVAR "CMDECHO" 0)	(setq new1 ";7%%13218 3/4")(XZZHYY2 new1)(setvar "CMDECHO" 1)(princ "已转换\n"))
(defun C:5720()(SETVAR "CMDECHO" 0)	(setq new1 ";7%%13220 3/4")(XZZHYY2 new1)(setvar "CMDECHO" 1)(princ "已转换\n"))
(defun C:5818()(SETVAR "CMDECHO" 0)	(setq new1 ";8%%13218 4/4")(XZZHYY2 new1)(setvar "CMDECHO" 1)(princ "已转换\n"))
(defun C:5820()(SETVAR "CMDECHO" 0)	(setq new1 ";8%%13220 4/4")(XZZHYY2 new1)(setvar "CMDECHO" 1)(princ "已转换\n"))

(defun C:509(/ new1)(SETVAR "CMDECHO" 0)	(setq new1 (cons 1 "2%%13214+1%%13216"))(XZZHYY new1 1)(setvar "CMDECHO" 1)(princ "已转换\n"))
(defun C:5622(/ new1)(SETVAR "CMDECHO" 0)	(setq new1 (cons 1 "2%%13214+1%%13218"))(XZZHYY new1 1)(setvar "CMDECHO" 1)(princ "已转换\n"))
(defun C:663(/ new1)(SETVAR "CMDECHO" 0)	(setq new1 (cons 1 "3%%13214+1%%13216"))(XZZHYY new1 1)(setvar "CMDECHO" 1)(princ "已转换\n"))
(defun C:710(/ new1)(SETVAR "CMDECHO" 0)	(setq new1 (cons 1 "2%%13214+2%%13216"))(XZZHYY new1 1)(setvar "CMDECHO" 1)(princ "已转换\n"))
(defun C:817(/ new1)(SETVAR "CMDECHO" 0)	(setq new1 (cons 1 "2%%13214+2%%13218"))(XZZHYY new1 1)(setvar "CMDECHO" 1)(princ "已转换\n"))

(defun C:330()
(SETVAR "CMDECHO" 0)	
(setq new1 (cons 1 "200x500"))
(XZZHYY new1 1)
(setvar "CMDECHO" 1)
(princ "已转换\n")
)


(defun C:331()
(SETVAR "CMDECHO" 0)	
(setq new1 (cons 1 "2%%13214"))
(XZZHYY new1 1)
(setvar "CMDECHO" 1)
(princ "已转换\n")
)

(defun C:332()
(SETVAR "CMDECHO" 0)	
(setq new1 (cons 1 "3%%13220(-1)"))
(XZZHYY new1 1)
(setvar "CMDECHO" 1)
(princ "已转换\n")
)

(defun C:333()
(SETVAR "CMDECHO" 0)	
(setq new1 (cons 1 "5%%13220 2/3"))
(XZZHYY new1 1)
(setvar "CMDECHO" 1)
(princ "已转换\n")
)

(defun C:334()
(SETVAR "CMDECHO" 0)	
(setq new1 (cons 1 "2%%13214+3%%13216"))
(XZZHYY new1 1)
(setvar "CMDECHO" 1)
(princ "已转换\n")
)

(defun C:381()
(SETVAR "CMDECHO" 0)	
(setq new1 (cons 1 "%%1328@100(2)"))
(XZZHYY new1 1)
(setvar "CMDECHO" 1)
(princ "已转换\n")
)
(defun C:382()
(SETVAR "CMDECHO" 0)	
(setq new1 (cons 1 "%%1328@200(2)"))
(XZZHYY new1 1)
(setvar "CMDECHO" 1)
(princ "已转换\n")
)
(defun C:361()
(SETVAR "CMDECHO" 0)	
(setq new1 (cons 1 "%%1326@100(2)"))
(XZZHYY new1 1)
(setvar "CMDECHO" 1)
(princ "已转换\n")
)
(defun C:362()
(SETVAR "CMDECHO" 0)	
(setq new1 (cons 1 "%%1326@200(2)"))
(XZZHYY new1 1)
(setvar "CMDECHO" 1)
(princ "已转换\n")
)
(defun C:3355()
(SETVAR "CMDECHO" 0)	
(setq new1 (cons 1 "%%1328@200"))
(XZZHYY new1 1)
(setvar "CMDECHO" 1)
(princ "已转换\n")
)

(defun C:3812()
(SETVAR "CMDECHO" 0)	
(setq new1 (cons 1 "%%1328@100/200(2)"))
(XZZHYY new1 1)
(setvar "CMDECHO" 1)
(princ "已转换\n")
)
(defun C:38120()
(SETVAR "CMDECHO" 0)	
(setq new1 (cons 1 "%%1328@100/200"))
(XZZHYY new1 1)
(setvar "CMDECHO" 1)
(princ "已转换\n")
)

(defun C:3612()
(SETVAR "CMDECHO" 0)	
(setq new1 (cons 1 "%%1326@100/200(2)"))
(XZZHYY new1 1)
(setvar "CMDECHO" 1)
(princ "已转换\n")
)

(defun C:36120()
(SETVAR "CMDECHO" 0)	
(setq new1 (cons 1 "%%1326@100/200"))
(XZZHYY new1 1)
(setvar "CMDECHO" 1)
(princ "已转换\n")
)


(defun C:337()
(SETVAR "CMDECHO" 0)	
(setq new1 (cons 1 "G2%%13212"))
(XZZHYY new1 1)
(setvar "CMDECHO" 1)
(princ "已转换\n")
)

(defun C:3372()
(SETVAR "CMDECHO" 0)	
(setq new1 (cons 1 "G4%%13212"))
(XZZHYY new1 1)
(setvar "CMDECHO" 1)
(princ "已转换\n")
)
(defun C:3373()
(SETVAR "CMDECHO" 0)	
(setq new1 (cons 1 "G2%%13210"))
(XZZHYY new1 1)
(setvar "CMDECHO" 1)
(princ "已转换\n")
)
(defun C:3374()
(SETVAR "CMDECHO" 0)	
(setq new1 (cons 1 "G4%%13210"))
(XZZHYY new1 1)
(setvar "CMDECHO" 1)
(princ "已转换\n")
)

(defun C:338()
(SETVAR "CMDECHO" 0)	
(setq new1 (cons 1 "N2%%13212"))
(XZZHYY new1 1)
(setvar "CMDECHO" 1)
(princ "已转换\n")
)

(defun C:339()
(SETVAR "CMDECHO" 0)	
(setq new1 (cons 1 "(-0.050)"))
(XZZHYY new1 1)
(setvar "CMDECHO" 1)
(princ "已转换\n")
)

(defun C:3392();;;改黄色
(SETVAR "CMDECHO" 0)	
(setq sel (ssget))
(if (/= sel Nil) 
(progn
(setq aa (sslength  sel))
(setq ii 0)
(while (< ii aa)
(setq first  (ssname sel ii)) 
(setq lst (entget first))
(setq new1 (cons 1 "(-0.050)"))
(setq lst (subst new1 (assoc 1 lst) lst))
(entmod lst) 
(command "change" first "" "p" "c" 2  "" ) 
(setq ii (+ ii 1))
)
)
)
(setvar "CMDECHO" 1)
(princ "已转换\n")
)






(defun C:1502(/ new1)
(SETVAR "CMDECHO" 0)	
(setq sel (ssget ))  
(if (/= sel Nil) 
(progn
(setq aa (sslength  sel))
(setq ii 0)
(while (< ii aa)
(setq first1  (ssname sel ii))
(setq lst (entget first1))
(setq new1 (cons 8 "S-DETL-TEXT"))
(setq lst (subst new1 (assoc 8 lst) lst))
(entmod lst)
(command "change" first1 "" "p" "c" "ByLayer"  "" )
(setq ii (+ ii 1))
)
)
) 
(setvar "CMDECHO" 1)
(princ "已转换\n"))



(defun C:774(/ new1)(SETVAR "CMDECHO" 0)	(setq new1 "修2")(XZZHYY2 new1)(setvar "CMDECHO" 1)(princ "已转换\n"))
(defun C:775(/ new1)(SETVAR "CMDECHO" 0)	(setq new1 (cons 1 "原图作废"))(XZZHYY new1 1)(setvar "CMDECHO" 1)(princ "已转换\n"))
(defun C:781(/ new1)(SETVAR "CMDECHO" 0)	(setq new1 (cons 1 "随屋面"))(XZZHYY new1 1)(setvar "CMDECHO" 1)(princ "已转换\n"))
(defun C:786(/ new1)(SETVAR "CMDECHO" 0)	(setq new1 (cons 1 "梁顶标高："))(XZZHYY new1 1)(setvar "CMDECHO" 1)(princ "已转换\n"))

(defun C:251(/ new1)
(SETVAR "CMDECHO" 0)	
(setq sel (ssget ))  
(if (/= sel Nil) 
(progn
(setq aa (sslength  sel))
(setq ii 0)
(while (< ii aa)
(setq first1  (ssname sel ii))
(command "change" first1 "" "p" "c" 251 "" )
(setq ii (+ ii 1))
)
)
) 
(setvar "CMDECHO" 1)
(princ "已转换\n"))


(defun C:782(/ new1)(SETVAR "CMDECHO" 0)	
(setq sel (ssget ))  
(if (/= sel Nil) 
(progn
(setq aa (sslength  sel))
(setq ii 0)
(while (< ii aa)
(setq first1  (ssname sel ii))
(command "change" first1 "" "p" "c" "ByLayer"  "" )
(setq ii (+ ii 1))
)
)
) 
(setvar "CMDECHO" 1)
(princ "已转换\n"))

(defun C:783(/ new1) ;;;用于在墙身详图中改字体和颜色
(SETVAR "CMDECHO" 0) 
(setq sel (ssget ))  
(if (/= sel Nil) 
(progn
(setq aa (sslength  sel))
(setq ii 0)
(while (< ii aa)
(setq first1  (ssname sel ii))
(setq lst (entget first1))
(setq laname (cdr (assoc 8 lst)))
(setq new (cons 8 "S-DETL-TEXT"))
 (setq lst (subst new (assoc 8 lst) lst))
 (entmod lst)
(command "change" first1 "" "p" "c" "ByLayer"  "" )
(setq ii (+ ii 1))
)
)
) 
(setvar "CMDECHO" 1)
(princ "已转换\n"))

(defun c:788(/ new1)(SETVAR "CMDECHO" 0)	(setq new1  "板顶附加：")(XZZHYY3 new1)(setvar "CMDECHO" 1)(princ "已转换\n"))
(defun c:7882(/ new1)(SETVAR "CMDECHO" 0)	(setq new1  "商铺")(XZZHYY3 new1)(setvar "CMDECHO" 1)(princ "已转换\n"))
(defun c:784(/ new1)(SETVAR "CMDECHO" 0)	(setq new1  "板顶：")(XZZHYY3 new1)(setvar "CMDECHO" 1)(princ "已转换\n"))
(defun c:785(/ new1)(SETVAR "CMDECHO" 0)	(setq new1  "板底：")(XZZHYY3 new1)(setvar "CMDECHO" 1)(princ "已转换\n"))


;;;***********转换标注样式*********;;;
(defun c:660( / new1)(SETVAR "CMDECHO" 0)(setq new1 (cons 3 "100"))(XZZHYY new1 3)(setvar "CMDECHO" 1)(princ "已转换为标注样式100\n"))
(defun c:661( / new1)(SETVAR "CMDECHO" 0)(setq new1 (cons 3 "50"))(XZZHYY new1 3)(setvar "CMDECHO" 1)(princ "已转换为标注样式50\n"))
(defun c:6632( / new1)(SETVAR "CMDECHO" 0)(setq new1 (cons 3 "20"))(XZZHYY new1 3)(setvar "CMDECHO" 1)(princ "已转换为标注样式20\n"));;;663与配筋有冲突，故改为6632
(defun c:667( / new1)(SETVAR "CMDECHO" 0)(setq new1 (cons 3 "50-100"))(XZZHYY new1 3)(setvar "CMDECHO" 1)(princ "已转换为标注样式50-100\n"))
(defun c:668( / new1)(SETVAR "CMDECHO" 0)(setq new1 (cons 3 "25-100"))(XZZHYY new1 3)(setvar "CMDECHO" 1)(princ "已转换为标注样式25-100\n"))

;;;***********转换文字字体*********;;;
(defun C:776(/ new1)(SETVAR "CMDECHO" 0)	(setq new1 (cons 7 "TSSD_REIN"))(XZZHYY new1 7)(setvar "CMDECHO" 1)(princ "已转换\n"))
(defun C:777(/ new1)(SETVAR "CMDECHO" 0)	(setq new1 (cons 41 0.75))(XZZHYY new1 41)(setvar "CMDECHO" 1)(princ "已转换\n"))



(defun C:778(/ new1)(SETVAR "CMDECHO" 0)	(setq new1 (cons 2 "dots"))(XZZHYY new1 2)(setvar "CMDECHO" 1)(princ "已转换\n"))
;;;***********转换字体高度*********;;;
(defun C:770(/ new1)(SETVAR "CMDECHO" 0)	(setq new1 (cons 40 300))(XZZHYY new1 40)(setvar "CMDECHO" 1)(princ "已转换\n"))
(defun C:771(/ new1)(SETVAR "CMDECHO" 0)	(setq new1 (cons 40 150))(XZZHYY new1 40)(setvar "CMDECHO" 1)(princ "已转换\n"))
(defun C:772(/ new1)(SETVAR "CMDECHO" 0)	(setq new1 (cons 40 75))(XZZHYY new1 40)(setvar "CMDECHO" 1)(princ "已转换\n"))
(defun C:773(/ new1)(SETVAR "CMDECHO" 0)	(setq new1 (cons 40 60))(XZZHYY new1 40)(setvar "CMDECHO" 1)(princ "已转换\n"))




;;;;;用于根据数字配筋：需要根据项目调整
(defun C:2003(/ new1)(SETVAR "CMDECHO" 0)	(setq new1 (cons 1 "2%%13216"))(XZZHYY new1 1)(setvar "CMDECHO" 1)(princ "已转换\n"))
(defun C:2004(/ new1)(SETVAR "CMDECHO" 0)	(setq new1 (cons 1 "3%%13216"))(XZZHYY new1 1)(setvar "CMDECHO" 1)(princ "已转换\n"))
(defun C:2005(/ new1)(SETVAR "CMDECHO" 0)	(setq new1 (cons 1 "3%%13216"))(XZZHYY new1 1)(setvar "CMDECHO" 1)(princ "已转换\n"))
(defun C:2006(/ new1)(SETVAR "CMDECHO" 0)	(setq new1 (cons 1 "3%%13218"))(XZZHYY new1 1)(setvar "CMDECHO" 1)(princ "已转换\n"))
(defun C:2007(/ new1)(SETVAR "CMDECHO" 0)	(setq new1 (cons 1 "3%%13218"))(XZZHYY new1 1)(setvar "CMDECHO" 1)(princ "已转换\n"))
(defun C:2008(/ new1)(SETVAR "CMDECHO" 0)	(setq new1 (cons 1 "5%%13216 2/3"))(XZZHYY new1 1)(setvar "CMDECHO" 1)(princ "已转换\n"))
(defun C:2009(/ new1)(SETVAR "CMDECHO" 0)	(setq new1 (cons 1 "5%%13216 2/3"))(XZZHYY new1 1)(setvar "CMDECHO" 1)(princ "已转换\n"))
(defun C:2010(/ new1)(SETVAR "CMDECHO" 0)	(setq new1 (cons 1 "5%%13218 2/3"))(XZZHYY new1 1)(setvar "CMDECHO" 1)(princ "已转换\n"))
(defun C:2011(/ new1)(SETVAR "CMDECHO" 0)	(setq new1 (cons 1 "5%%13218 2/3"))(XZZHYY new1 1)(setvar "CMDECHO" 1)(princ "已转换\n"))
(defun C:2012(/ new1)(SETVAR "CMDECHO" 0)	(setq new1 (cons 1 "5%%13220 2/3"))(XZZHYY new1 1)(setvar "CMDECHO" 1)(princ "已转换\n"))
(defun C:2013(/ new1)(SETVAR "CMDECHO" 0)	(setq new1 (cons 1 "5%%13220 2/3"))(XZZHYY new1 1)(setvar "CMDECHO" 1)(princ "已转换\n"))
(defun C:2014(/ new1)(SETVAR "CMDECHO" 0)	(setq new1 (cons 1 "5%%13220 2/3"))(XZZHYY new1 1)(setvar "CMDECHO" 1)(princ "已转换\n"))
(defun C:2015(/ new1)(SETVAR "CMDECHO" 0)	(setq new1 (cons 1 "5%%13222 2/3"))(XZZHYY new1 1)(setvar "CMDECHO" 1)(princ "已转换\n"))
(defun C:2016(/ new1)(SETVAR "CMDECHO" 0)	(setq new1 (cons 1 "5%%13222 2/3"))(XZZHYY new1 1)(setvar "CMDECHO" 1)(princ "已转换\n"))
(defun C:2017(/ new1)(SETVAR "CMDECHO" 0)	(setq new1 (cons 1 "5%%13222 2/3"))(XZZHYY new1 1)(setvar "CMDECHO" 1)(princ "已转换\n"))
(defun C:2018(/ new1)(SETVAR "CMDECHO" 0)	(setq new1 (cons 1 "6%%13222 3/3"))(XZZHYY new1 1)(setvar "CMDECHO" 1)(princ "已转换\n"))
(defun C:2019(/ new1)(SETVAR "CMDECHO" 0)	(setq new1 (cons 1 "6%%13222 3/3"))(XZZHYY new1 1)(setvar "CMDECHO" 1)(princ "已转换\n"))
(defun C:2020(/ new1)(SETVAR "CMDECHO" 0)	(setq new1 (cons 1 "6%%13222 3/3"))(XZZHYY new1 1)(setvar "CMDECHO" 1)(princ "已转换\n"))
(defun C:2021(/ new1)(SETVAR "CMDECHO" 0)	(setq new1 (cons 1 "6%%13222 3/3"))(XZZHYY new1 1)(setvar "CMDECHO" 1)(princ "已转换\n"))
(defun C:2024(/ new1)(SETVAR "CMDECHO" 0)	(setq new1 (cons 1 "6%%13225 3/3"))(XZZHYY new1 1)(setvar "CMDECHO" 1)(princ "已转换\n"))

(defun C:2503(/ new1)(SETVAR "CMDECHO" 0)	(setq new1 (cons 1 "2%%13216"))(XZZHYY new1 1)(setvar "CMDECHO" 1)(princ "已转换\n"))
(defun C:2504(/ new1)(SETVAR "CMDECHO" 0)	(setq new1 (cons 1 "3%%13216"))(XZZHYY new1 1)(setvar "CMDECHO" 1)(princ "已转换\n"))
(defun C:2505(/ new1)(SETVAR "CMDECHO" 0)	(setq new1 (cons 1 "3%%13216"))(XZZHYY new1 1)(setvar "CMDECHO" 1)(princ "已转换\n"))
(defun C:2506(/ new1)(SETVAR "CMDECHO" 0)	(setq new1 (cons 1 "3%%13218"))(XZZHYY new1 1)(setvar "CMDECHO" 1)(princ "已转换\n"))
(defun C:2507(/ new1)(SETVAR "CMDECHO" 0)	(setq new1 (cons 1 "3%%13218"))(XZZHYY new1 1)(setvar "CMDECHO" 1)(princ "已转换\n"))
(defun C:2508(/ new1)(SETVAR "CMDECHO" 0)	(setq new1 (cons 1 "5%%13216"))(XZZHYY new1 1)(setvar "CMDECHO" 1)(princ "已转换\n"))
(defun C:2509(/ new1)(SETVAR "CMDECHO" 0)	(setq new1 (cons 1 "5%%13216"))(XZZHYY new1 1)(setvar "CMDECHO" 1)(princ "已转换\n"))
(defun C:2510(/ new1)(SETVAR "CMDECHO" 0)	(setq new1 (cons 1 "5%%13218"))(XZZHYY new1 1)(setvar "CMDECHO" 1)(princ "已转换\n"))
(defun C:2511(/ new1)(SETVAR "CMDECHO" 0)	(setq new1 (cons 1 "5%%13218"))(XZZHYY new1 1)(setvar "CMDECHO" 1)(princ "已转换\n"))
(defun C:2512(/ new1)(SETVAR "CMDECHO" 0)	(setq new1 (cons 1 "5%%13220 2/3"))(XZZHYY new1 1)(setvar "CMDECHO" 1)(princ "已转换\n"))
(defun C:2513(/ new1)(SETVAR "CMDECHO" 0)	(setq new1 (cons 1 "5%%13220 2/3"))(XZZHYY new1 1)(setvar "CMDECHO" 1)(princ "已转换\n"))
(defun C:2514(/ new1)(SETVAR "CMDECHO" 0)	(setq new1 (cons 1 "5%%13220 2/3"))(XZZHYY new1 1)(setvar "CMDECHO" 1)(princ "已转换\n"))
(defun C:2515(/ new1)(SETVAR "CMDECHO" 0)	(setq new1 (cons 1 "5%%13222 2/3"))(XZZHYY new1 1)(setvar "CMDECHO" 1)(princ "已转换\n"))
(defun C:2516(/ new1)(SETVAR "CMDECHO" 0)	(setq new1 (cons 1 "5%%13222 2/3"))(XZZHYY new1 1)(setvar "CMDECHO" 1)(princ "已转换\n"))
(defun C:2517(/ new1)(SETVAR "CMDECHO" 0)	(setq new1 (cons 1 "5%%13222 2/3"))(XZZHYY new1 1)(setvar "CMDECHO" 1)(princ "已转换\n"))
(defun C:2518(/ new1)(SETVAR "CMDECHO" 0)	(setq new1 (cons 1 "5%%13222 2/3"))(XZZHYY new1 1)(setvar "CMDECHO" 1)(princ "已转换\n"))
(defun C:2519(/ new1)(SETVAR "CMDECHO" 0)	(setq new1 (cons 1 "6%%13222 2/4"))(XZZHYY new1 1)(setvar "CMDECHO" 1)(princ "已转换\n"))
(defun C:2521(/ new1)(SETVAR "CMDECHO" 0)	(setq new1 (cons 1 "6%%13222 2/4"))(XZZHYY new1 1)(setvar "CMDECHO" 1)(princ "已转换\n"))
(defun C:2524(/ new1)(SETVAR "CMDECHO" 0)	(setq new1 (cons 1 "6%%13225 2/4"))(XZZHYY new1 1)(setvar "CMDECHO" 1)(princ "已转换\n"))
(defun C:2525(/ new1)(SETVAR "CMDECHO" 0)	(setq new1 (cons 1 "6%%13225 2/4"))(XZZHYY new1 1)(setvar "CMDECHO" 1)(princ "已转换\n"))

(defun C:3003(/ new1)(SETVAR "CMDECHO" 0)	(setq new1 (cons 1 "2%%13216"))(XZZHYY new1 1)(setvar "CMDECHO" 1)(princ "已转换\n"))
(defun C:3004(/ new1)(SETVAR "CMDECHO" 0)	(setq new1 (cons 1 "3%%13216"))(XZZHYY new1 1)(setvar "CMDECHO" 1)(princ "已转换\n"))
(defun C:3005(/ new1)(SETVAR "CMDECHO" 0)	(setq new1 (cons 1 "3%%13216"))(XZZHYY new1 1)(setvar "CMDECHO" 1)(princ "已转换\n"))
(defun C:3006(/ new1)(SETVAR "CMDECHO" 0)	(setq new1 (cons 1 "3%%13218"))(XZZHYY new1 1)(setvar "CMDECHO" 1)(princ "已转换\n"))
(defun C:3007(/ new1)(SETVAR "CMDECHO" 0)	(setq new1 (cons 1 "3%%13218"))(XZZHYY new1 1)(setvar "CMDECHO" 1)(princ "已转换\n"))
(defun C:3008(/ new1)(SETVAR "CMDECHO" 0)	(setq new1 (cons 1 "5%%13216"))(XZZHYY new1 1)(setvar "CMDECHO" 1)(princ "已转换\n"))
(defun C:3009(/ new1)(SETVAR "CMDECHO" 0)	(setq new1 (cons 1 "5%%13216"))(XZZHYY new1 1)(setvar "CMDECHO" 1)(princ "已转换\n"))
(defun C:3010(/ new1)(SETVAR "CMDECHO" 0)	(setq new1 (cons 1 "5%%13218"))(XZZHYY new1 1)(setvar "CMDECHO" 1)(princ "已转换\n"))
(defun C:3011(/ new1)(SETVAR "CMDECHO" 0)	(setq new1 (cons 1 "5%%13218"))(XZZHYY new1 1)(setvar "CMDECHO" 1)(princ "已转换\n"))
(defun C:3012(/ new1)(SETVAR "CMDECHO" 0)	(setq new1 (cons 1 "5%%13220"))(XZZHYY new1 1)(setvar "CMDECHO" 1)(princ "已转换\n"))
(defun C:3013(/ new1)(SETVAR "CMDECHO" 0)	(setq new1 (cons 1 "5%%13220"))(XZZHYY new1 1)(setvar "CMDECHO" 1)(princ "已转换\n"))
(defun C:3014(/ new1)(SETVAR "CMDECHO" 0)	(setq new1 (cons 1 "5%%13220"))(XZZHYY new1 1)(setvar "CMDECHO" 1)(princ "已转换\n"))
(defun C:3015(/ new1)(SETVAR "CMDECHO" 0)	(setq new1 (cons 1 "5%%13222"))(XZZHYY new1 1)(setvar "CMDECHO" 1)(princ "已转换\n"))
(defun C:3016(/ new1)(SETVAR "CMDECHO" 0)	(setq new1 (cons 1 "5%%13222"))(XZZHYY new1 1)(setvar "CMDECHO" 1)(princ "已转换\n"))
(defun C:3017(/ new1)(SETVAR "CMDECHO" 0)	(setq new1 (cons 1 "5%%13222"))(XZZHYY new1 1)(setvar "CMDECHO" 1)(princ "已转换\n"))
(defun C:3018(/ new1)(SETVAR "CMDECHO" 0)	(setq new1 (cons 1 "5%%13222"))(XZZHYY new1 1)(setvar "CMDECHO" 1)(princ "已转换\n"))
(defun C:3020(/ new1)(SETVAR "CMDECHO" 0)	(setq new1 (cons 1 "6%%13222 2/4"))(XZZHYY new1 1)(setvar "CMDECHO" 1)(princ "已转换\n"))
(defun C:3021(/ new1)(SETVAR "CMDECHO" 0)	(setq new1 (cons 1 "6%%13222 2/4"))(XZZHYY new1 1)(setvar "CMDECHO" 1)(princ "已转换\n"))
(defun C:3022(/ new1)(SETVAR "CMDECHO" 0)	(setq new1 (cons 1 "5%%13225 2/3"))(XZZHYY new1 1)(setvar "CMDECHO" 1)(princ "已转换\n"))
(defun C:3024(/ new1)(SETVAR "CMDECHO" 0)	(setq new1 (cons 1 "6%%13225 2/4"))(XZZHYY new1 1)(setvar "CMDECHO" 1)(princ "已转换\n"))
(defun C:3025(/ new1)(SETVAR "CMDECHO" 0)	(setq new1 (cons 1 "6%%13225 2/4"))(XZZHYY new1 1)(setvar "CMDECHO" 1)(princ "已转换\n"))
(defun C:3026(/ new1)(SETVAR "CMDECHO" 0)	(setq new1 (cons 1 "6%%13225 2/4"))(XZZHYY new1 1)(setvar "CMDECHO" 1)(princ "已转换\n"))
(defun C:3028(/ new1)(SETVAR "CMDECHO" 0)	(setq new1 (cons 1 "7%%13225 2/5"))(XZZHYY new1 1)(setvar "CMDECHO" 1)(princ "已转换\n"))
(defun C:3029(/ new1)(SETVAR "CMDECHO" 0)	(setq new1 (cons 1 "7%%13225 2/5"))(XZZHYY new1 1)(setvar "CMDECHO" 1)(princ "已转换\n"))
(defun C:3030(/ new1)(SETVAR "CMDECHO" 0)	(setq new1 (cons 1 "7%%13225 2/5"))(XZZHYY new1 1)(setvar "CMDECHO" 1)(princ "已转换\n"))
(defun C:3031(/ new1)(SETVAR "CMDECHO" 0)	(setq new1 (cons 1 "7%%13225 2/5"))(XZZHYY new1 1)(setvar "CMDECHO" 1)(princ "已转换\n"))

(defun XZZHYY(new2 type / sel aa ii first lst)
(setq sel (ssget))
(if (/= sel Nil) 
(progn
(setq aa (sslength  sel))
(setq ii 0)
(while (< ii aa)
(setq first  (ssname sel ii)) 
(setq lst (entget first))
(setq lst (subst new2 (assoc type lst) lst))
(entmod lst) 
(setq ii (+ ii 1))
)
)
)  
)



(defun XZZHYY2(new1 / sel aa ii first lst new0 new3 old0)
(setq sel (ssget '((0 . "TEXT"))))
(if (/= sel Nil)
(progn
(setq aa (sslength  sel))
(setq ii 0)
(while (< ii aa)
(setq first  (ssname sel ii))
(setq lst (entget first))
(setq old0 (cdr (assoc 1 lst))) ;;; 
(setq new0 (strcat old0 new1)) ;;; 
(setq new3 (cons 1 new0))
(setq lst (subst new3 (assoc 1 lst) lst))
(entmod lst)
(setq ii (+ ii 1))
)
)
)
)

(defun XZZHYY3(new1 / sel aa ii first lst new0 new3 old0)
(setq sel (ssget '((0 . "TEXT"))))
(if (/= sel Nil)
(progn
(setq aa (sslength  sel))
(setq ii 0)
(while (< ii aa)
(setq first  (ssname sel ii))
(setq lst (entget first))
(setq old0 (cdr (assoc 1 lst))) ;;; 
(setq new0 (strcat  new1 old0)) ;;; 
(setq new3 (cons 1 new0))
(setq lst (subst new3 (assoc 1 lst) lst))
(entmod lst)
(setq ii (+ ii 1))
)
)
)
)



(defun DQXGYY(new2 new3)
(setq sel (ssget '((0  . "TEXT"))))
(if (/= sel Nil)
(progn
(setq aa (sslength  sel))
(setq ii 0)
(while (< ii aa)
(setq first  (ssname sel ii))
(setq lst (entget first))
(setq lst (subst new2 (assoc 72 lst) lst))
(setq lst (subst new3 (assoc 73 lst) lst))
(entmod lst)
(setq ii (+ ii 1))
)
)
)
)

(defun XGQZYY(newpre)
(setq sel (ssget  '((0 . "TEXT")(8 . "S-BEAM-*")) ))
(if (/= sel Nil) 
(progn
(setq aa (sslength  sel))
(setq ii 0)
(while (< ii aa)	
(setq first  (ssname sel ii)) 
(setq lst (entget first)) 
(setq newtext (cdr (assoc 1 lst))) 
(setq tpre (substr newtext 1 1))
(if (= tpre "K") (setq tpre (substr newtext 1 2)) )
(if (= tpre "W") (setq tpre (substr newtext 1 2)) )
(cond
	((= tpre "KL") (setq Num 3))
	((= tpre "KZ") (setq Num 4))
	((= tpre "L") (setq Num 2))
	((= tpre "WL") (setq Num 3))
	((= tpre "WK") (setq Num 4))
	((= tpre "X") (setq Num 3))
	(T (setq Num 0))
)
(if (/= Num 0) 
(progn
(setq new1 (strcat newpre (substr newtext Num)  ))
(setq new2 (cons 1 new1 ))
(setq lst (subst new2 (assoc 1 lst) lst))
(entmod lst)
)
)
(setq ii (+ ii 1))
)
)
)
)

(defun XGQZYY2(newpre)
(setq sel (ssget  '((0 . "TEXT")) ))
(if (/= sel Nil) 
(progn
(setq aa (sslength  sel))
(setq ii 0)
(while (< ii aa)	
(setq first  (ssname sel ii)) 
(setq lst (entget first)) 
(setq newtext (cdr (assoc 1 lst))) 
(setq tpre (substr newtext 1 1))
(if (= tpre "K") (setq tpre (substr newtext 1 2)) )
(cond
	((= tpre "KL") (setq Num 3))
	((= tpre "KZ") (setq Num 4))
	((= tpre "L") (setq Num 2))
	((= tpre "W") (setq Num 4))
	((= tpre "X") (setq Num 3))
	(T (setq Num 0))
)
(if (/= Num 0) 
(progn
(setq new1 (strcat newpre  newtext   ))
(setq new2 (cons 1 new1 ))
(setq lst (subst new2 (assoc 1 lst) lst))
(entmod lst)
)
)
(setq ii (+ ii 1))
)
)
)
)
